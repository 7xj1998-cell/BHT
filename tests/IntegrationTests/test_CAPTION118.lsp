(setq c118-checks 0 c118-fails 0)
(defun c118-check (name ok)
  (setq c118-checks (1+ c118-checks)) (if (not ok) (setq c118-fails (1+ c118-fails)))
  (princ (strcat "\n" (if ok "PASS CAPTION118 " "FAIL CAPTION118 ") name)))
(defun c118-labels (id)
  (mapcar 'cdr (vl-remove-if-not '(lambda (pr) (= (car pr) id)) (bht:tagged-pairs "TEXT" "BHT_KH" 1))))
(defun c118-station (id) (car (vl-remove-if-not 'bht:kh-station-label-p (c118-labels id))))
(defun c118-shape (id) (mapcar '(lambda (e) (entget e '("*"))) (c118-labels id)))
(defun c118-aligned (id / title d a h rot good i row pos)
  (setq title (car (vl-remove-if 'bht:kh-extra-label-p (c118-labels id))) d (entget title)
        a (cdr (assoc 11 d)) h (cdr (assoc 40 d)) rot (cdr (assoc 50 d)) good T)
  (foreach row (c118-labels id)
    (setq d (entget row) pos (cdr (assoc 11 d))
          i (if (bht:kh-station-label-p row) 2 (if (bht:kh-extra-face-label-p row) 1 0)))
    (if (or (not (equal pos (polar a (- rot (/ pi 2)) (* i 1.5 h)) 1e-7))
            (not (equal h (cdr (assoc 40 d)) 1e-7)) (not (equal rot (cdr (assoc 50 d)) 1e-7))) (setq good nil))) good)
(defun c118-above (id / e d a bounds text local h good)
  (setq e (cdr (assoc id (bht:tagged-pairs "INSERT" "BHT_KH" 1))) d (entget e)
        a (list (cdr (assoc 10 d)) (abs (cdr (assoc 41 d))) (cdr (assoc 50 d)))
        bounds (BHTSIGNBOUNDS (cdr (assoc 2 d))) good T)
  (foreach text (c118-labels id)
    (setq d (entget text) h (cdr (assoc 40 d)) local (bht:kh-caption-local (cdr (assoc 11 d)) a))
    (if (< (- (cadr local) h) (* (cadr a) (nth 3 bounds))) (setq good nil))) good)
(bht:meta-set "symbol_leader_mode" "THANG")
(foreach row '(("OTHER118" "KHAC" 0.0 0.0 1.5707963268) ("AD118" "BANG_QC" 20.0 0.0 0.0)
              ("UNKNOWN118" "CHUA_XAC_DINH" 40.0 0.0 3.1415926536)
              ("MULTI118" "BIEN_BAO" 60.0 0.0 1.5707963268) ("SINGLE118" "BIEN_BAO" 80.0 0.0 -1.5707963268))
  (setq id (car row) e (entmakex (list '(0 . "POINT") (cons 10 (list (nth 2 row) (nth 3 row) 0.0)))))
  (bht:pt-write-xdata e id "QA" "1" id (nth 3 row) (nth 2 row) 0.0 (cadr row) "QA" "" "")
  (bht:obj-create id (list (cons "nhom" (cadr row)) '("mo_ta" . "ĐỊA PHẬN XÃ ĐỨC HÒA") '("so_tru" . "2") '("ma_hieu" . "W.239a")) (list id) T)
  (setq rec (bht:set (bht:obj-read id) "ly_trinh_km" "Km48+525.03"))
  (if (= id "MULTI118") (setq rec (bht:set-all (bht:set rec "so_mat" "2") "mat" '("W.239a" "S.509a"))))
  (bht:obj-write id rec)
  (bht:kh-free-apply-mode id (list (+ 4 (nth 2 row)) 15.0 0.0) (nth 4 row) nil "THANG"))
(foreach id '("OTHER118" "AD118" "UNKNOWN118")
  (c118-check (strcat "named-board-station-only-" id) (and (= 1 (length (c118-labels id))) (c118-station id)
    (= "Km48+525.03" (cdr (assoc 1 (entget (c118-station id))))))))
(c118-check "multi-face-three-aligned-rows" (and (= 3 (length (c118-labels "MULTI118"))) (c118-aligned "MULTI118")))
(c118-check "named-board-chainage-centered-above-face" (c118-above "OTHER118"))
(c118-check "single-opposite-rotation-has-station" (= 2 (length (c118-labels "SINGLE118"))))
(foreach c118-angle (list 0.0 (/ pi 2.0) pi (* 1.5 pi))
  (bht:kh-free-apply-mode "MULTI118" '(64.0 15.0 0.0) c118-angle nil "THANG")
  (c118-check (strcat "stack-aligned-at-rotation-" (rtos c118-angle 2 2)) (and (c118-aligned "MULTI118") (c118-above "MULTI118"))))
(setq c118-missing-rec (bht:obj-read "SINGLE118"))
(bht:obj-write "SINGLE118" (bht:set (bht:set c118-missing-rec "so_mat" "0") "tinh_trang" "Mất mặt biển, còn trụ"))
(bht:symbol-sync '("SINGLE118"))
(c118-check "missing-face-still-has-location-chainage" (and (= 1 (length (c118-labels "SINGLE118"))) (c118-station "SINGLE118")))
(bht:obj-write "SINGLE118" c118-missing-rec) (bht:symbol-sync '("SINGLE118"))
(setq c118-before (c118-shape "MULTI118") c118-board (c118-shape "OTHER118"))
(bht:symbol-sync '("MULTI118" "OTHER118"))
(c118-check "first-and-second-render-stable" (and (equal c118-before (c118-shape "MULTI118")) (equal c118-board (c118-shape "OTHER118"))))
;; Manual primary moves the complete stack, instead of splitting off extra codes.
(setq e (car (vl-remove-if 'bht:kh-extra-label-p (c118-labels "MULTI118"))) d (entget e) c118-manual '(72.0 22.0 0.0))
(entmod (bht:dxf-put (bht:dxf-put d 10 c118-manual) 11 c118-manual)) (entupd e)
(bht:symbol-sync '("MULTI118"))
(c118-check "manual-caption-retained-and-stack-follows" (and (equal c118-manual (cdr (assoc 11 (entget e))) 1e-7) (c118-aligned "MULTI118")))
(setq c118-inserts (mapcar '(lambda (pr) (entget (cdr pr) '("*"))) (bht:tagged-pairs "INSERT" "BHT_KH" 1)) c118-points (bht:pt-all))
(bht:obj-write "OTHER118" (bht:set (bht:obj-read "OTHER118") "ly_trinh_km" "Km49+001.25"))
(bht:kh-station-label-refresh '("OTHER118"))
(c118-check "station-refresh-updates-named-board-text" (= "Km49+001.25" (cdr (assoc 1 (entget (c118-station "OTHER118"))))))
(c118-check "station-refresh-keeps-inserts-and-survey" (and (equal c118-inserts (mapcar '(lambda (pr) (entget (cdr pr) '("*"))) (bht:tagged-pairs "INSERT" "BHT_KH" 1))) (equal c118-points (bht:pt-all))))
(bht:obj-write "AD118" (bht:set (bht:obj-read "AD118") "ly_trinh_km" ""))
(bht:kh-station-label-refresh '("AD118"))
(c118-check "cleared-station-removes-stale-text" (null (c118-station "AD118")))
;; Geometry and stored chainage must agree after both individual and route calculations.
(setq c118-route (entmakex '((0 . "LWPOLYLINE") (100 . "AcDbEntity") (100 . "AcDbPolyline") (90 . 2) (70 . 0) (10 0.0 0.0) (10 100.0 0.0))))
(bht:route-create "R118" c118-route "TIM_DUONG" 50.0 0.0 nil "QA")
(bht:route-add-mark "R118" 0.0 48525.03 48525.03 "QA A" "")
(bht:route-add-mark "R118" 30.0 48555.03 48555.03 "QA B" "")
(bht:meta-set "station_method" "ROUTE")
(bht:station-one "OTHER118")
(c118-check "single-station-calculation-refreshes-visible-board" (= "Km48+525.03" (cdr (assoc 1 (entget (c118-station "OTHER118"))))))
(defun c118-all-snapshot () (list (bht:rec-all "OBJ") (bht:rec-read "META" "CONFIG") (mapcar '(lambda (pr) (entget (cdr pr) '("*"))) (bht:tagged-pairs "TEXT" "BHT_KH" 1))))
(setq c118-rollback-before (c118-all-snapshot) c118-sync-old bht:kh-sync-station-label c118-call-count 0)
(defun bht:kh-sync-station-label (id record blk anchor texts)
  (setq c118-call-count (1+ c118-call-count))
  (if (= c118-call-count 2) (/ 1 0) (c118-sync-old id record blk anchor texts)))
(setq c118-rollback-result (bht:route-recalculate "R118") bht:kh-sync-station-label c118-sync-old)
(c118-check "station-caption-failure-restores-records-and-text" (and (eq (car c118-rollback-result) 'LOI) (equal c118-rollback-before (c118-all-snapshot))))
(bht:route-recalculate "R118")
(c118-check "route-calculation-refreshes-and-clears-stale-captions" (and (c118-station "AD118") (null (c118-station "MULTI118")) (null (c118-station "UNKNOWN118"))))
(c118-check "route-station-refresh-keeps-placement-and-survey" (and (equal c118-inserts (mapcar '(lambda (pr) (entget (cdr pr) '("*"))) (bht:tagged-pairs "INSERT" "BHT_KH" 1))) (equal c118-points (bht:pt-all))))
(bht:layer "QA_FRONT118" 1)
(entmakex '((0 . "SOLID") (8 . "QA_FRONT118") (10 0.0 0.0 0.0) (11 100.0 0.0 0.0) (12 0.0 100.0 0.0) (13 100.0 100.0 0.0)))
(bht:kh-labels-front)
(c118-check "captions-above-later-solid" (> (CAPTION118ORDER) 0))
(princ (strcat "\nCAPTION118-CHECKS=" (itoa c118-checks) " FAIL=" (itoa c118-fails))) (princ)
