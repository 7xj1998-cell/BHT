(setq q123-count 0 q123-fail 0)
(defun q123-check (name ok) (setq q123-count (1+ q123-count)) (if (not ok) (setq q123-fail (1+ q123-fail))) (princ (strcat "\n" (if ok "PASS ROUTE123 " "FAIL ROUTE123 ") name)))
(setq q123-line (entmakex '((0 . "LWPOLYLINE") (100 . "AcDbEntity") (100 . "AcDbPolyline") (90 . 2) (70 . 0) (10 0.0 0.0) (10 200.0 0.0))))
(bht:route-create "R123" q123-line "TIM_DUONG" 20.0 0.0 nil "TDTSolution test")
(bht:route-add-mark "R123" 100.0 50240.0 50240.0 "TDT_STAKES A" "giữ nguyên ghi chú")
(bht:route-add-mark "R123" 0.0 50140.0 50140.0 "TDT_STAKES B" "")
(bht:route-add-mark "R123" 80.0 50220.0 50230.0 "TDT_STAKES C" "điểm gãy")
(setq q123-original (bht:route-read "R123") q123-geometry (entget q123-line) q123-rows (bht:route-mark-rows q123-original))
(q123-check "rows-retain-original-indices-before-display-sort" (and (bht:starts (nth 0 q123-rows) "0|100.") (bht:starts (nth 1 q123-rows) "1|0.") (bht:starts (nth 2 q123-rows) "2|80.")))
(q123-check "type-input-alias-and-Vietnamese" (and (= "TIM_RANH" (bht:route-type "R")) (= "TIM_RANH" (bht:route-type "Tim rãnh")) (= "TIM_DUONG" (bht:route-type "tim_duong")) (null (bht:route-type "unknown"))))
(q123-check "no-change-edit-keeps-revision-and-marks" (and (car (bht:route-edit "R123" "R123" "TIM_DUONG" 20.0 0.0)) (equal q123-original (bht:route-read "R123"))))
(q123-check "change-to-ditch-type-preserves-controls-and-geometry" (and (car (bht:route-edit "R123" "R123" "R" 20.5 0.0)) (= "TIM_RANH" (bht:get (bht:route-read "R123") "loai")) (equal (bht:get-all q123-original "moc") (bht:get-all (bht:route-read "R123") "moc")) (equal q123-geometry (entget q123-line))))
(setq q123-current (bht:route-read "R123"))
(q123-check "bad-type-gives-specific-error-no-change" (and (not (car (bht:route-edit "R123" "R123" "bad" 20.0 0.0))) (equal q123-current (bht:route-read "R123"))))
(q123-check "bad-number-does-not-mutate" (and (not (car (bht:route-edit "R123" "R123" "TIM_RANH" nil 0.0))) (not (car (bht:route-edit "R123" "R123" "TIM_RANH" 20.0 -1.0))) (equal q123-current (bht:route-read "R123"))))
(q123-check "stale-table-rejected-before-delete" (and (eq 'LOI (car (bht:route-delete-marks "R123" q123-original '(0)))) (equal q123-current (bht:route-read "R123"))))
(foreach q123-bad '((-1) (9) (0 0) (0.5) (nil))
  (q123-check "invalid-row-selection-rejected" (and (eq 'LOI (car (bht:route-delete-marks "R123" q123-current q123-bad))) (equal q123-current (bht:route-read "R123")))))
(bht:obj-write "Q123-OBJ" '(("nhom" . "BIEN_BAO") ("route_id" . "R123") ("ly_trinh_m" . "50200") ("offset_m" . "2") ("station_status" . "OK")))
(bht:obj-write "Q123-MARK" '(("nhom" . "COC_TIEU") ("route_id" . "R123") ("marker_km" . "50") ("marker_h" . "2") ("ly_trinh_m" . "50200.000")))
(setq q123-objs (bht:rec-all "OBJ"))
(setq q123-invalidate bht:route-invalidate-objects)
(defun bht:route-invalidate-objects (id detached) (bht:obj-write "Q123-OBJ" '(("nhom" . "KHAC"))) (/ 1 0))
(q123-check "delete-failure-rolls-back-route-and-object-records" (and (eq 'LOI (car (bht:route-delete-marks "R123" q123-current '(0)))) (equal q123-current (bht:route-read "R123")) (equal q123-objs (bht:rec-all "OBJ"))))
(setq bht:route-invalidate-objects q123-invalidate)
(q123-check "multi-delete-targets-stored-rows-not-sorted-indices" (and (not (eq 'LOI (car (bht:route-delete-marks "R123" q123-current '(0 2))))) (equal (bht:get-all (bht:route-read "R123") "moc") (list (nth 1 (bht:get-all q123-current "moc"))))))
(q123-check "delete-invalidates-derived-station-keeps-observed-marker" (and (= "" (bht:get (bht:obj-read "Q123-OBJ") "ly_trinh_m")) (= "STALE" (bht:get (bht:obj-read "Q123-OBJ") "station_status")) (= "50200.000" (bht:get (bht:obj-read "Q123-MARK") "ly_trinh_m"))))
(q123-check "delete-preserves-alignment-geometry" (equal q123-geometry (entget q123-line)))
(q123-check "view-raw-distance-forward" (= 80.0 (bht:route-mark-raw q123-current 80.0)))
(q123-check "view-raw-distance-reverse-with-start-offset" (= 120.0 (bht:route-mark-raw (bht:set (bht:set q123-current "direction" "-1") "start_dist" "200") 80.0)))
(q123-check "view-outside-open-alignment-rejected" (and (null (bht:route-mark-raw q123-current 201.0)) (null (bht:route-mark-raw q123-current -1.0))))
(setq q123-preview (bht:route-mark-preview '(80.0 0.0 0.0)))
(q123-check "view-marker-centered-at-exact-station-point" (and (= 3 (length q123-preview)) (equal '(80.0 0.0 0.0) (cdr (assoc 10 (entget (car q123-preview))))) (= "CIRCLE" (cdr (assoc 0 (entget (car q123-preview)))))))
(bht:route-preview-clear q123-preview)
(q123-check "view-marker-cleanup" (vl-every '(lambda (e) (null (entget e))) q123-preview))
(setq q123-damaged (bht:set-all q123-current "moc" (append (bht:get-all q123-current "moc") '(""))))
(q123-check "damaged-row-still-visible-for-removal" (= 4 (length (bht:route-mark-rows q123-damaged))))
(bht:route-write "R123" q123-current)
(foreach q123-pair q123-objs (bht:obj-write (car q123-pair) (cdr q123-pair)))
;; Drive the public commands through the same dialog return contract without displaying a modal in Core Console.
(setq q123-real-options BHTROUTEOPTIONS q123-real-marks BHTROUTEMARKS)
(defun BHTROUTEOPTIONS (title id type maxoff extrap) q123-option-reply)
(defun BHTROUTEMARKS (route row0 row1 row2 / answer) (setq answer (car q123-mark-replies) q123-mark-replies (cdr q123-mark-replies)) answer)
;; Exercise the TDT command boundary; the native adapter itself is unchanged.
(setq q123-entsel entsel q123-bridge BHTTDT91ROUTE q123-pick-start bht:route-pick-start
      q123-source (entmakex '((0 . "POINT") (10 15.0 15.0 0.0)))
      q123-ref (entmakex '((0 . "LWPOLYLINE") (100 . "AcDbEntity") (100 . "AcDbPolyline") (90 . 2) (70 . 0) (10 0.0 10.0) (10 200.0 10.0)))
      q123-source-data (entget q123-source) q123-native-calls 0)
(defun entsel (prompt) (list q123-source '(15.0 15.0 0.0)))
(defun BHTTDT91ROUTE (source handle) (setq q123-native-calls (1+ q123-native-calls)) (list "OK" (cdr (assoc 5 (entget q123-ref))) "TdtDbAlignment"))
(defun bht:route-pick-start (id) T)
(setq q123-option-reply '("CANCEL"))
(c:BHTTUYENTDT)
(q123-check "cancel-TDT-options-does-not-call-native-adapter" (= q123-native-calls 0))
(setq q123-option-reply '("OK" "TDT123" "TIM_RANH" "20.5" "0"))
(c:BHTTUYENTDT)
(q123-check "TDT-create-uses-selected-ditch-type" (and (= q123-native-calls 1) (= "TIM_RANH" (bht:get (bht:route-read "TDT123") "loai")) (= "20.500" (bht:get (bht:route-read "TDT123") "max_offset"))))
(bht:route-add-mark "TDT123" 0.0 1000.0 1000.0 "TDT_STAKES" "")
(c:BHTTUYENTDT)
(q123-check "TDT-refresh-preserves-type-controls-and-source" (and (= q123-native-calls 2) (= "TIM_RANH" (bht:get (bht:route-read "TDT123") "loai")) (= 1 (length (bht:route-marks (bht:route-read "TDT123")))) (equal q123-source-data (entget q123-source))))
(setq entsel q123-entsel BHTTDT91ROUTE q123-bridge bht:route-pick-start q123-pick-start)
(setq q123-option-reply '("CANCEL") *bht-route-selected* "R123")
(c:BHTSUATUYEN)
(q123-check "dialog-cancel-does-not-edit" (equal q123-current (bht:route-read "R123")))
(setq q123-mark-replies '(("CANCEL")) *bht-route-selected* "R123")
(c:BHTDSMOC)
(q123-check "table-close-does-not-delete" (equal q123-current (bht:route-read "R123")))
(defun BHTROUTEMARKS (route row0 row1 row2)
  (defun BHTROUTEMARKS (route row0 row1) '("CANCEL"))
  '("DELETE" "1"))
(princ (strcat "\nROUTE123-CHECKS=" (itoa q123-count) " FAIL=" (itoa q123-fail)))
(princ)
