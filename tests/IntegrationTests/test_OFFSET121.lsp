(setq o121-n 0 o121-fail 0)
(defun o121-check (name ok) (setq o121-n (1+ o121-n)) (if (not ok) (setq o121-fail (1+ o121-fail))) (princ (strcat "\n" (if ok "PASS OFFSET121 " "FAIL OFFSET121 ") name)))
(defun o121-point (id x y z / e) (setq e (entmakex (list '(0 . "POINT") (cons 10 (list x y z))))) (bht:pt-write-xdata e id "QA" "1" id y x z "BIEN_BAO" "QA" "" ""))
(defun o121-route (id y / e) (setq e (entmakex (list '(0 . "LWPOLYLINE") '(100 . "AcDbEntity") '(100 . "AcDbPolyline") '(90 . 2) '(70 . 0) (cons 10 (list 0.0 y)) (cons 10 (list 1000.0 y)))))
  (bht:route-create id e "TIM_RANH" 100.0 0.0 nil "OFFSET121") (bht:route-add-mark id 0.0 48000.0 48000.0 "QA" "") (bht:route-add-mark id 1000.0 49000.0 49000.0 "QA" ""))
(defun o121-sign (id group poles points) (bht:obj-create id (list (cons "nhom" group) (cons "so_tru" poles) '("ma_hieu" . "W.239a") '("mo_ta" . "Biển kiểm tra")) points T))
(defun o121-value (id key) (bht:get (bht:obj-read id) key))
(defun o121-origins (id) (vl-remove-if-not '(lambda (p) (= (car p) id)) (bht:tagged-pairs "INSERT" "BHT_SIGN_ORIGIN" 1)))
(o121-route "ROAD121" 0.0) (o121-route "DITCH121" 20.0)
(o121-point "NEAR121" 100.0 2.0 125.0) (o121-point "FAR121" 110.0 6.0 225.0)
(o121-sign "TWO121" "BANG_CHI_DAN" "2" '("FAR121" "NEAR121"))
(bht:meta-set "station_method" "ROUTE") (bht:meta-set "station_active_route" "ROAD121")
(setq o121-index (bht:pt-all) o121-centroid (bht:obj-position (bht:obj-read "TWO121") o121-index))
(o121-check "presentation-centroid-preserved" (equal o121-centroid '(105.0 4.0 175.0) 1e-8))
(bht:station-one "TWO121")
(o121-check "two-post-offset-nearest-not-centroid-XY" (= "2.000" (o121-value "TWO121" "offset_m")))
(o121-check "station-and-offset-use-same-nearest-post" (and (= "48100.000" (o121-value "TWO121" "ly_trinh_m")) (= "NEAR121" (o121-value "TWO121" "station_point_id"))))
(o121-check "station-provenance-has-survey-and-projection" (and (= "100.000000" (o121-value "TWO121" "station_point_e")) (= "2.000000" (o121-value "TWO121" "station_point_n")) (= "0.000000" (o121-value "TWO121" "station_projection_n"))))
(setq o121-tie (bht:set-all (bht:obj-read "TWO121") "pt" '("FAR121" "TIE121")))
(o121-point "TIE121" 120.0 6.0 99.0)
(o121-check "equal-distance-tie-stable-by-point-id" (= "FAR121" (car (bht:station-support o121-tie (bht:pt-all) (bht:route-read "ROAD121") nil))))
(setq o121-reverse (bht:set (bht:set (bht:route-read "ROAD121") "direction" "-1") "start_dist" "1000"))
(o121-check "reversing-route-keeps-nearest-support-and-reverses-side" (and (= "NEAR121" (cdr (assoc 'point_id (bht:station-object-route o121-reverse (bht:obj-read "TWO121") o121-index o121-centroid)))) (= "PHAI" (cdr (assoc 'side (bht:station-object-route o121-reverse (bht:obj-read "TWO121") o121-index o121-centroid))))))
(setq o121-start (bht:set (bht:route-read "ROAD121") "start_dist" "105"))
(o121-check "nearest-before-start-does-not-switch-to-farther-valid-support" (and (= "NEAR121" (cdr (assoc 'point_id (bht:station-object-route o121-start (bht:obj-read "TWO121") o121-index o121-centroid)))) (not (bht:station-determined (cdr (assoc 'status (bht:station-object-route o121-start (bht:obj-read "TWO121") o121-index o121-centroid)))))))
(bht:rec-write "ROUTE" "AA-BROKEN121" '(("route_id" . "AA-BROKEN121") ("handle" . "0") ("max_offset" . "100")))
(bht:meta-set "station_active_route" "")
(o121-check "auto-route-skips-missing-geometry-before-valid-route" (= "ROAD121" (cdr (assoc 'route (bht:station-object (bht:obj-read "TWO121") o121-index o121-centroid)))))
(bht:rec-delete "ROUTE" "AA-BROKEN121") (bht:meta-set "station_active_route" "ROAD121")
(setq o121-shape (entget (bht:pv (bht:pt-find "NEAR121" o121-index) 'ent) '("*")))
(bht:station-objects)
(o121-check "bulk-offset-uses-same-post-as-single" (= "2.000" (o121-value "TWO121" "offset_m")))
(bht:route-recalculate "ROAD121")
(o121-check "explicit-route-recalc-nearest-post" (and (= "2.000" (o121-value "TWO121" "offset_m")) (= "NEAR121" (o121-value "TWO121" "station_point_id"))))
(bht:rec-write "SEG" "DITCH-SEG121" '(("segment_id" . "DITCH-SEG121") ("package_id" . "GOI121") ("route_id" . "DITCH121") ("km_start_m" . "48000") ("km_end_m" . "49000") ("side" . "HAI_BEN")))
(bht:assign-manual "TWO121" "DITCH-SEG121")
(o121-check "bound-ditch-nearest-post-differs-from-road" (and (= "14.000" (o121-value "TWO121" "offset_m")) (= "FAR121" (o121-value "TWO121" "station_point_id")) (= "48110.000" (o121-value "TWO121" "ly_trinh_m"))))
(bht:meta-set "station_method" "FIELD_MARKERS") (bht:station-objects)
(o121-check "field-mode-bound-route-retains-nearest-post" (= "14.000" (o121-value "TWO121" "offset_m")))
(bht:meta-set "station_method" "ROUTE")
(bht:obj-write "TWO121" (bht:set (bht:obj-read "TWO121") "gan_doan_pp" "")) (bht:assign-segments)
(o121-check "segment-options-use-bound-route-nearest-post" (and (= "DITCH-SEG121" (o121-value "TWO121" "doan")) (= "14.000" (o121-value "TWO121" "offset_m"))))
(o121-point "ONE121" 150.0 2.262 122.192) (o121-sign "OTHER121" "KHAC" "1" '("ONE121"))
(o121-point "ADP121" 170.0 3.0 0.0) (o121-sign "AD121" "BANG_QC" "1" '("ADP121"))
(o121-point "UNP121" 190.0 4.0 0.0) (o121-sign "UNKNOWN121" "CHUA_XAC_DINH" "1" '("UNP121"))
(o121-point "MKP121" 210.0 3.0 0.0) (o121-sign "MARKER121" "COC_TIEU" "1" '("MKP121"))
(bht:station-one "OTHER121") (bht:symbol-sync '("TWO121" "OTHER121" "AD121" "UNKNOWN121" "MARKER121"))
(o121-check "other-sign-single-post-origin-dot" (= 1 (length (o121-origins "OTHER121"))))
(o121-check "all-other-sign-groups-have-origin-dot" (and (= 1 (length (o121-origins "AD121"))) (= 1 (length (o121-origins "UNKNOWN121")))))
(o121-check "guide-board-two-posts-have-both-dots" (= 2 (length (o121-origins "TWO121"))))
(o121-check "markers-excluded-from-sign-origin-dots" (null (o121-origins "MARKER121")))
(bht:symbol-sync '("TWO121" "OTHER121"))
(o121-check "origin-refresh-idempotent" (and (= 2 (length (o121-origins "TWO121"))) (= 1 (length (o121-origins "OTHER121")))))
(setq o121-dot (cdr (car (o121-origins "OTHER121"))))
(o121-check "dot-at-true-survey-X-not-shifted-symbol" (equal (cdr (assoc 10 (entget o121-dot))) '(150.0 2.262 122.192) 1e-8))
(setq o121-result (bht:offset-dimension "OTHER121")) (prin1 o121-result)
(o121-check "dimension-single-post-XY-ignores-height" (not (eq (car o121-result) 'LOI)))
(setq o121-result (bht:offset-dimension "TWO121")) (prin1 o121-result)
(o121-check "dimension-two-post-bound-route" (not (eq (car o121-result) 'LOI)))
(bht:offset-dimension "TWO121")
(o121-check "dimension-refresh-does-not-duplicate" (= 2 (length (bht:tagged-pairs "DIMENSION" "BHT_OFFSET_DIM" 1))))
(o121-check "survey-points-never-moved" (equal o121-shape (entget (bht:pv (bht:pt-find "NEAR121" (bht:pt-all)) 'ent) '("*"))))
(o121-check "missing-object-dimension-rejected" (eq (car (bht:offset-dimension "MISSING121")) 'LOI))
(princ (strcat "\nOFFSET121-CHECKS=" (itoa o121-n) " FAIL=" (itoa o121-fail)))
