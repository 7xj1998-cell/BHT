(setq s114-count 0 s114-fails 0)
(defun s114-check (name ok)
  (setq s114-count (1+ s114-count))
  (if (not ok) (setq s114-fails (1+ s114-fails)))
  (princ (strcat "\n" (if qa110-baseline "BASELINE " (if ok "PASS " "FAIL ")) "SCOPE114 " name "=" (if ok "OK" "FAILED"))))
(defun s114-obj (id x y / pid ent)
  (setq pid (strcat id "-P") ent (entmakex (list '(0 . "POINT") (cons 10 (list x y 0.0)))))
  (bht:pt-write-xdata ent pid "QA" "1" id y x 0.0 "BIEN_BAO" "QA" "" "")
  (bht:obj-create id '(("nhom" . "BIEN_BAO") ("ma_hieu" . "P.102") ("phia_duong" . "TRAI")) (list pid) T))
(defun s114-snapshot ()
  (list (bht:rec-all "OBJ") (bht:rec-all "SEG") (bht:rec-all "ROUTE") (bht:rec-all "META")
    (mapcar '(lambda (p) (entget (bht:pv (cdr p) 'ent) '("*"))) (bht:pt-all))))
(setq s114-line (entmakex '((0 . "LWPOLYLINE") (100 . "AcDbEntity") (100 . "AcDbPolyline") (90 . 2) (70 . 0) (10 0.0 0.0) (10 75.0 0.0))))
(bht:route-create "R01" s114-line "TIM_DUONG" 30.0 0.0 1 "QA")
(bht:route-add-mark "R01" 0.0 38622.0 38622.0 "QA" "")
(bht:route-add-mark "R01" 75.0 38697.0 38697.0 "QA" "")
(setq s114-route (bht:route-read "R01") s114-geometry (entget s114-line))
(foreach s114-case '(("before-start" -1.0 2.0) ("after-end" 76.0 2.0) ("after-end-on-axis" 80.0 0.0))
  (setq s114-r (bht:station-route s114-route (list (cadr s114-case) (caddr s114-case) 0.0)))
  (s114-check (car s114-case) (and (= "NGOAI_PHAM_VI_HINH_HOC" (cdr (assoc 'status s114-r))) (null (cdr (assoc 'station s114-r))))))
(foreach s114-case '(("start-perpendicular" 0.0 38622.0) ("end-perpendicular" 75.0 38697.0) ("inside" 30.0 38652.0))
  (setq s114-r (bht:station-route s114-route (list (cadr s114-case) 2.0 0.0)))
  (s114-check (car s114-case) (equal (caddr s114-case) (cdr (assoc 'station s114-r)) 1e-6)))
(setq s114-reverse (bht:set (bht:set s114-route "direction" "-1") "start_dist" "75"))
(s114-check "reverse-rejects-beyond-both-ends" (and (null (bht:route-project s114-reverse s114-line '(-2.0 1.0 0.0))) (null (bht:route-project s114-reverse s114-line '(77.0 1.0 0.0)))))
(s114-check "reverse-interior-distance" (equal 25.0 (car (bht:route-project s114-reverse s114-line '(50.0 2.0 0.0))) 1e-6))
(s114-check "interior-start-excludes-earlier-station" (null (bht:route-project (bht:set s114-route "start_dist" "25") s114-line '(20.0 2.0 0.0))))
(bht:rec-write "SEG" "DOAN_01" '(("segment_id" . "DOAN_01") ("package_id" . "GOI_01") ("km_start_m" . "38622") ("km_end_m" . "38697") ("side" . "HAI_BEN") ("route_id" . "R01")))
(s114-obj "INSIDE" 20.0 2.0)
(s114-obj "OUT6" 76.0 2.0)
(s114-obj "OUT7" 80.0 3.0)
(s114-obj "OUT8" 85.0 2.0)
(setq s114-before (s114-snapshot) s114-plan (bht:progress-plan "DOAN_01" "R01"))
(s114-check "preview-only-inside-not-three-clamped-signs" (equal '("INSIDE") (mapcar 'car (nth 2 s114-plan))))
(s114-check "preview-no-write" (equal s114-before (s114-snapshot)))
(bht:progress-apply s114-plan)
(s114-check "outside-signs-unchanged" (not (vl-some '(lambda (id) (not (equal (cdr (assoc id (car s114-before))) (bht:obj-read id)))) '("OUT6" "OUT7" "OUT8"))))
(setq s114-result (bht:kh-display-transaction 'bht:progress-finish (list "DOAN_01")))
(s114-check "only-inside-confirmed" (and (eq (car s114-result) T) (equal '("INSIDE") (mapcar 'car (vl-remove-if-not '(lambda (p) (bht:progress-locked (cdr p))) (bht:rec-all "OBJ"))))))
;; A manually assigned object must still satisfy the segment station interval.
(bht:rec-write "SEG" "SHORT" '(("segment_id" . "SHORT") ("package_id" . "GOI_01") ("km_start_m" . "38622") ("km_end_m" . "38640") ("side" . "HAI_BEN") ("route_id" . "R01")))
(s114-obj "MANUAL" 50.0 2.0)
(bht:assign-manual-write "MANUAL" "SHORT")
(setq s114-before (s114-snapshot) s114-plan (bht:progress-plan "SHORT" "R01"))
(s114-check "manual-outside-segment-not-eligible" (null (nth 2 s114-plan)))
(setq s114-result (bht:kh-display-transaction 'bht:progress-finish (list "SHORT")))
(s114-check "manual-outside-cannot-confirm" (and (eq (car s114-result) 'LOI) (equal s114-before (s114-snapshot))))
(s114-check "route-geometry-unchanged" (equal s114-geometry (entget s114-line)))
;; Circular arc endpoint tangents, including a route with reversed direction.
(setq s114-arc (entmakex '((0 . "LWPOLYLINE") (100 . "AcDbEntity") (100 . "AcDbPolyline") (90 . 2) (70 . 0) (10 0.0 0.0) (42 . 1.0) (10 100.0 0.0))))
(bht:route-create "ARC" s114-arc "TIM_DUONG" 30.0 0.0 1 "QA")
(setq s114-arcr (bht:route-read "ARC"))
(s114-check "arc-start-outward" (null (bht:route-project s114-arcr s114-arc '(-2.0 3.0 0.0))))
(s114-check "arc-end-outward" (null (bht:route-project s114-arcr s114-arc '(102.0 3.0 0.0))))
(s114-check "arc-end-normal-valid" (bht:route-project s114-arcr s114-arc '(102.0 0.0 0.0)))
(s114-check "arc-interior-valid" (bht:route-project s114-arcr s114-arc '(50.0 -52.0 0.0)))
(setq s114-closed (entmakex '((0 . "LWPOLYLINE") (100 . "AcDbEntity") (100 . "AcDbPolyline") (90 . 4) (70 . 1) (10 0.0 0.0) (10 100.0 0.0) (10 100.0 100.0) (10 0.0 100.0))))
(bht:route-create "CLOSED" s114-closed "TIM_DUONG" 30.0 0.0 1 "QA")
(s114-check "closed-route-seam-remains-valid" (bht:route-project (bht:route-read "CLOSED") s114-closed '(-2.0 -2.0 0.0)))
;; Unsuccessful attempts may retain the attempted route for diagnosis, never a segment.
(bht:meta-set "station_active_route" "R01")
(s114-obj "FAR" 20.0 12500.0)
(setq s114-locked (bht:obj-read "INSIDE") s114-rtk (bht:pt-all))
(bht:station-objects-base)
(s114-check "far-attempt-no-valid-station-or-assignment" (and (= "OUT_OF_RANGE" (bht:get (bht:obj-read "FAR") "station_status")) (= "" (bht:get (bht:obj-read "FAR") "ly_trinh_m")) (= "" (bht:get (bht:obj-read "FAR") "doan"))))
(s114-check "global-calculation-keeps-confirmed-record-and-rtk" (and (equal s114-locked (bht:obj-read "INSIDE")) (equal s114-rtk (bht:pt-all))))
;; A rejected first route must not break the search for another valid route.
(setq s114-ids-fn bht:route-ids)
(defun bht:route-ids () '("R01" "ARC"))
(bht:meta-set "station_active_route" "")
(setq s114-r (vl-catch-all-apply 'bht:station (list '(102.0 0.0 0.0))) bht:route-ids s114-ids-fn)
(s114-check "rejected-first-route-does-not-break-next-route" (and (not (vl-catch-all-error-p s114-r)) (= "ARC" (cdr (assoc 'route s114-r)))))
(princ (strcat "\nSCOPE114-DONE=" (itoa s114-count) " FAIL=" (itoa s114-fails)))
(princ "\nQA110-DONE")
(princ)
