;;; BHT 1.1.5 - phien T: anh nen IRT dang LUOI NHIEU TILE (moi tile = 1 IMAGE rieng, khong phai xref)
;;; 144 tile (12x12) + 12 tile tren layer KHOA. Ten file / layer KHONG khop mau mac dinh -> phai dat mau.
(load "C:/Users/Le Bao/BHT_TEST_V044/t_common.lsp")
(tbegin "T")
(setq e (tload))
(tchk "T00" "nạp BHT-5.0" (and (null e) (= *bht-version* "1.1.5")) e)
(setq r (tsafe "T01" "nhập survey.csv (526 điểm + nhãn)" '(lambda () (bht:import-csv (strcat *T-DIR* "data/survey.csv") "BOT19"))))
(setq P (bht:pt-all) x0 nil x1 nil y0 nil y1 nil)
(foreach it P (setq c (bht:pv (cdr it) 'xyz)
                    x0 (if x0 (min x0 (car c)) (car c)) x1 (if x1 (max x1 (car c)) (car c))
                    y0 (if y0 (min y0 (cadr c)) (cadr c)) y1 (if y1 (max y1 (cadr c)) (cadr c))))
(setq PC0 (t-pt-coords) cw (/ (- x1 x0) 12.0) chh (/ (- y1 y0) 12.0) cs (max cw chh))
(bht:layer "NEN_ANH" 7) (bht:layer "NEN_KHOA" 7)
(setq cl (getvar "CLAYER")) (setvar "CMDECHO" 0) (setvar "CLAYER" "NEN_ANH")
(setq TILES nil t0 (getvar "MILLISECS") ri 0)
(while (< ri 12)
  (setq ci 0)
  (while (< ci 12)
    (setq le (entlast))
    (vl-cmdf "_.-IMAGE" "_Attach" (strcat *T-DIR* "nen/tiles/L18_" (itoa ri) "_" (itoa ci) ".jpg")
             (list (+ x0 (* ci cs)) (+ y0 (* ri cs)) 0.0) cs 0.0)
    (while (= 1 (logand 1 (getvar "CMDACTIVE"))) (command ""))
    (if (not (equal le (entlast))) (setq TILES (cons (entlast) TILES)))
    (setq ci (1+ ci)))
  (setq ri (1+ ri)))
(setvar "CLAYER" "NEN_KHOA") (setq LOCKED nil ci 0)
(while (< ci 12)
  (setq le (entlast))
  (vl-cmdf "_.-IMAGE" "_Attach" (strcat *T-DIR* "nen/tiles/L18_K_" (itoa ci) ".jpg") (list (+ x0 (* ci cs)) (- y0 cs) 0.0) cs 0.0)
  (while (= 1 (logand 1 (getvar "CMDACTIVE"))) (command ""))
  (if (not (equal le (entlast))) (setq LOCKED (cons (entlast) LOCKED)))
  (setq ci (1+ ci)))
(setvar "CLAYER" cl)
(tlog (strcat "   đã chèn " (itoa (length TILES)) " + " (itoa (length LOCKED)) " tile, " (itoa (- (getvar "MILLISECS") t0)) " ms"))
(tchk "T02" "tạo lưới 144 tile + 12 tile layer khóa (IMAGE riêng, mỗi tile 1 file)" (and (= (length TILES) 144) (= (length LOCKED) 12)) (list (length TILES) (length LOCKED)))
(setq TD (mapcar 'entget (append TILES LOCKED)))
(command "_.-LAYER" "_Lock" "NEN_KHOA" "")
;; 1) mau mac dinh: ten L18_* / layer NEN_* khong khop -> KHONG dung vao
(setq g (bht:draworder-groups))
(tchk "T03" "mẫu mặc định không khớp -> 156 tile là 'không chắc chắn', KHÔNG bị coi là IRT"
      (and (= (length (cdr (assoc 'irt g))) 0) (= (length (cdr (assoc 'other-images g))) 156)) (list (length (cdr (assoc 'irt g))) (length (cdr (assoc 'other-images g)))))
;; 2) dat mau ten file (cau hinh trong ban ve, giong BHTTHUTUVE > C)
(bht:meta-set "irt_mau_file" "L18_*")
(setq t0 (getvar "MILLISECS") g (bht:draworder-groups) tg (- (getvar "MILLISECS") t0))
(tchk "T04" "mẫu tên file L18_* -> nhận đủ 156 tile là IRT; 12 tile trên layer khóa được đếm riêng"
      (and (= (length (cdr (assoc 'irt g))) 156) (= (cdr (assoc 'irt-locked g)) 12) (= (length (cdr (assoc 'other-images g))) 0))
      (list (length (cdr (assoc 'irt g))) (cdr (assoc 'irt-locked g)) (strcat (itoa tg) " ms phân loại")))
(setq t0 (getvar "MILLISECS") n (bht:draworder-sync) ts (- (getvar "MILLISECS") t0))
(bht:draworder-report n)
(tchk "T05" "BHTTHUTUVE với 156 tile: 1 lệnh DRAWORDER cho cả lưới, chạy xong < 60 s" (and n (< ts 60000)) (strcat (itoa ts) " ms | " (vl-princ-to-string n)))
(setq se (t-sortents) g (bht:draworder-groups)
      bhtr (t-rank-range (append (cdr (assoc 'labels g)) (cdr (assoc 'mid g))) se)
      tr (t-rank-range TILES se) kr (t-rank-range LOCKED se))
(tchk "T06" "144 tile (layer mở) nằm DƯỚI toàn bộ nhãn / POINT BHT (bảng SORTENTS)" (and (car bhtr) (cadr tr) (< (cadr tr) (car bhtr))) (list 'tile tr 'bht bhtr))
(tlog (strcat "INFO T07 tile trên layer KHÓA sau DRAWORDER: hạng " (vl-princ-to-string kr) " so với BHT " (vl-princ-to-string bhtr)
              (if (and (cadr kr) (car bhtr) (< (cadr kr) (car bhtr))) " -> cũng đã xuống dưới" " -> KHÔNG được đưa xuống (DRAWORDER bỏ qua layer khóa; BHT chỉ báo, không mở khóa)")))
(tchk "T08" "dữ liệu 156 tile không bị sửa (chỉ bảng thứ tự hiển thị)" (equal (mapcar 'entget (append TILES LOCKED)) TD) nil)
(tchk "T09" "layer NEN_KHOA vẫn khóa (BHT không mở khóa)" (bht:layer-locked-p "NEN_KHOA") nil)
;; 3) mau theo layer
(bht:meta-set "irt_mau_file" *bht-irt-file-pat*) (bht:meta-set "irt_mau_lop" "NEN_ANH,NEN_KHOA")
(setq g (bht:draworder-groups))
(tchk "T10" "mẫu theo layer NEN_ANH,NEN_KHOA -> 156 IRT" (= (length (cdr (assoc 'irt g))) 156) (length (cdr (assoc 'irt g))))
(bht:meta-set "irt_mau_lop" *bht-irt-layer-pat*)
;; 4) 0.4.0: tile IRTv6 nam tren layer 0 (layer hien hanh) trong thu muc bo nho dem ...\IRT\... -> nhan theo DUONG DAN
(setvar "CLAYER" "0")
(setq le (entlast)) (vl-cmdf "_.-IMAGE" "_Attach" (strcat *T-DIR* "gia_irt/IRT/sat/18/t_1.jpg") (list x0 (- y0 (* 3 cs)) 0.0) cs 0.0)
(while (= 1 (logand 1 (getvar "CMDACTIVE"))) (command ""))
(setq G0 (if (not (equal le (entlast))) (entlast)))
(setq le (entlast)) (vl-cmdf "_.-IMAGE" "_Attach" (strcat *T-DIR* "khac/anh_khac_0.jpg") (list (+ x0 cs) (- y0 (* 3 cs)) 0.0) cs 0.0)
(while (= 1 (logand 1 (getvar "CMDACTIVE"))) (command ""))
(setq G1 (if (not (equal le (entlast))) (entlast)))
(setvar "CLAYER" cl)
(setq g (bht:draworder-groups) G1D (if G1 (entget G1)))
(tchk "T12" "layer 0 + đường dẫn ...\\IRT\\sat\\18\\t_1.jpg (mẫu mặc định) -> là IRT; ảnh khác trên layer 0 -> KHÔNG phải IRT"
      (and G0 G1 (member G0 (cdr (assoc 'irt g))) (member G1 (cdr (assoc 'other-images g))) (not (member G1 (cdr (assoc 'irt g)))))
      (list G0 G1 (length (cdr (assoc 'irt g))) (length (cdr (assoc 'other-images g)))))
(setq se (t-sortents) r1 (if G1 (t-rank G1 se)))
(bht:draworder-sync)
(setq se (t-sortents) bhtr (t-rank-range (append (cdr (assoc 'labels g)) (cdr (assoc 'mid g))) se))
(setq irr (t-rank-range (cdr (assoc 'irt g)) se))
(tchk "T13" "sau BHTTHUTUVE: tile layer 0 (thư mục IRT) xuống dưới BHT; ảnh khác KHÔNG bị đưa xuống (vẫn trên mọi tile IRT), dữ liệu không đổi"
      (and G0 G1 (< (t-rank G0 se) (car bhtr)) (> (t-rank G1 se) (cadr irr)) (equal (entget G1) G1D))
      (list 'irt (if G0 (t-rank G0 se)) 'khac r1 (if G1 (t-rank G1 se)) 'bht bhtr))
(tchk "T11" "không POINT nào bị dời" (equal (vl-sort PC0 '(lambda (a b) (< (car a) (car b)))) (vl-sort (t-pt-coords) '(lambda (a b) (< (car a) (car b))))) nil)
(tend "T")
(princ)
