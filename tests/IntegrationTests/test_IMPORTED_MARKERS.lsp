(setq imported-fails 0 imported-passes 0)
(defun ic (name ok) (if ok (setq imported-passes (1+ imported-passes)) (setq imported-fails (1+ imported-fails))) (princ (strcat "\n" (if ok "PASS INPUT " "FAIL INPUT ") name)))
(defun im (id x y km h / e)
  (setq e (entmakex (list '(0 . "POINT") (cons 10 (list x y 0.0)))))
  (bht:pt-write-xdata e id "INPUT-QA" "1" id y x 0.0 "COC_TIEU" "QA" "" "")
  (bht:obj-write id (list (cons "object_id" id) '("nhom" . "COC_TIEU") (cons "marker_km" km) (cons "marker_h" h) (cons "pt" id))) e)
(im "C" 200.0 0.0 "40" "2") (im "A" 0.0 0.0 "40" "0") (setq ib (im "B" 100.0 0.0 "40" "1"))
(im "KM" 1000.0 0.0 "41" "") (bht:obj-write "KM" (bht:set (bht:obj-read "KM") "nhom" "COT_KM"))
(im "HAND" 400.0 0.0 "40" "4") (bht:obj-write "HAND" (bht:set (bht:obj-read "HAND") "position_source" "MANUAL_CAD"))
(im "EMPTY" 500.0 0.0 "" "")
(setq iv (bht:api-field-input-preview) snap (cadr iv))
(ic "preview-OK" (= "OK" (car iv)))
(ic "preview-includes-unapproved-manual" (= 8 (length iv)))
(ic "sorted-by-station" (equal '("A" "B" "C" "KM") (mapcar 'car (bht:field-input-rows (bht:pt-all)))))
(ic "preview-read-only" (null (bht:rec-read "FIELD_CHAIN" "BHT_IMPORTED_MARKERS")))
(ic "stale-preview-rejected" (= "LOI" (car (bht:api-field-input-use "old"))))
(ic "activate-without-manual-chain" (= "OK" (car (bht:api-field-input-use snap))))
(ic "mode-set-explicitly" (and (bht:field-mode-p) (= "BHT_IMPORTED_MARKERS" (bht:meta "field_active_chain" ""))))
(setq ie (entmakex '((0 . "POINT") (10 50.0 2.0 0.0))))
(bht:pt-write-xdata ie "SIGNPT" "QA" "2" "SIGN" 2.0 50.0 0.0 "BIEN_BAO" "QA" "" "")
(bht:obj-write "SIGN" '(("object_id" . "SIGN") ("nhom" . "BIEN_BAO") ("pt" . "SIGNPT") ("ly_trinh_m" . "123")))
(ic "calculate-imported" (= "OK" (car (bht:api-object-station "SIGN"))))
(ic "station-and-pair-visible" (and (= "A" (bht:get (bht:obj-read "SIGN") "field_used_a")) (= "B" (bht:get (bht:obj-read "SIGN") "field_used_b")) (equal 40050.0 (atof (bht:get (bht:obj-read "SIGN") "ly_trinh_m")) 1e-6)))
(setq before (bht:obj-read "SIGN"))
(bht:obj-write "B" (bht:set (bht:obj-read "B") "marker_h" "2"))
(ic "edited-marker-requires-review" (= "COC_DA_THAY_DOI" (cdr (assoc 'status (bht:field-result before '(50.0 2.0 0.0) (bht:pt-all))))))
(ic "failed-calc-retains-record" (and (= "LOI" (car (bht:api-object-station "SIGN"))) (equal before (bht:obj-read "SIGN"))))
(setq iv (bht:api-field-input-preview))
(ic "duplicate-stations-not-deduplicated" (= 8 (length iv)))
(bht:api-field-input-use (cadr iv))
(ic "duplicate-neighbour-blocked" (= "COC_CAN_DOI_CHIEU" (cdr (assoc 'status (bht:field-result nil '(50.0 2.0 0.0) (bht:pt-all))))))
(bht:obj-write "B" (bht:set (bht:obj-read "B") "marker_h" "1"))
(bht:api-field-input-use (cadr (bht:api-field-input-preview)))
(entmod (subst '(10 101.0 0.0 0.0) (assoc 10 (entget ib)) (entget ib)))
(ic "moved-RTK-requires-review" (= "COC_DA_THAY_DOI" (cdr (assoc 'status (bht:field-result nil '(50.0 2.0 0.0) (bht:pt-all))))))
(entmod (subst '(10 100.0 0.0 0.0) (assoc 10 (entget ib)) (entget ib)))
(bht:obj-delete "B")
(ic "deleted-marker-not-bridged" (= "COC_DA_THAY_DOI" (cdr (assoc 'status (bht:field-result nil '(50.0 2.0 0.0) (bht:pt-all))))))
(bht:api-field-input-use (cadr (bht:api-field-input-preview)))
(ic "review-allows-new-neighbours" (= "NOI_SUY" (cdr (assoc 'status (bht:field-result nil '(50.0 2.0 0.0) (bht:pt-all))))))
(im "D" 100.0 0.0 "40" "3")
(bht:api-field-input-use (cadr (bht:api-field-input-preview)))
(ic "reversal-blocked" (bht:get-all (bht:rec-read "FIELD_CHAIN" "BHT_IMPORTED_MARKERS") "blocked_pair"))
(ic "reviewed-pair-can-override-local-warning" (= "OK" (car (bht:api-field-pair "SIGN" "A" "C"))))
(ic "explicit-pair-preserved" (and (= "A" (bht:get (bht:obj-read "SIGN") "field_pair_a")) (= "OK" (car (bht:api-object-station "SIGN")))))
(bht:obj-delete "D")
(bht:api-field-input-use (cadr (bht:api-field-input-preview)))
(bht:api-field-auto "SIGN")
(ic "reserved-group-not-editable" (= "LOI" (car (bht:api-field-save "BHT_IMPORTED_MARKERS" "test" "A C" "100" "500" "0.03"))))
(setq iv (bht:api-field-input-preview) before (bht:obj-read "SIGN"))
(bht:api-field-input-use (cadr iv))
(ic "unchanged-review-does-not-stale-results" (equal before (bht:obj-read "SIGN")))
(bht:field-objects)
(ic "batch-cache-imported" (= "VALID" (bht:get (bht:obj-read "SIGN") "station_status")))
(ic "manual-in-preview-not-control" (and (vl-some '(lambda (s) (vl-string-search "[MANUAL_OFF]" s)) (cdr (bht:api-field-input-preview))) (null (bht:field-marker "HAND" (bht:pt-all)))))
(ic "real-marker-cannot-be-manual-approved" (= "LOI" (car (bht:api-field-manual-control "A" "1"))))
(bht:obj-write "EMPTY" (bht:set (bht:obj-read "EMPTY") "position_source" "MANUAL_CAD"))
(ic "incomplete-manual-visible" (vl-some '(lambda (s) (vl-string-search "EMPTY|NaN" s)) (cdr (bht:api-field-input-preview))))
(ic "incomplete-not-approvable" (= "LOI" (car (bht:api-field-manual-control "EMPTY" "1"))))
(ic "approve-hand" (= "OK" (car (bht:api-field-manual-control "HAND" "1"))))
(ic "approved-eligible-with-source" (= "MANUAL_CAD" (nth 3 (bht:field-marker "HAND" (bht:pt-all)))))
(ic "approval-requires-list-review" (= "COC_DA_THAY_DOI" (cdr (assoc 'status (bht:field-result nil '(350.0 1.0 0.0) (bht:pt-all))))))
(bht:api-field-input-use (cadr (bht:api-field-input-preview)))
(setq mr (bht:field-result nil '(350.0 1.0 0.0) (bht:pt-all)))
(ic "manual-interpolation" (and (= "1" (cdr (assoc 'manual_control mr))) (equal 40350.0 (cdr (assoc 'station mr)) 1e-6)))
(setq stored (bht:field-store-result (bht:obj-read "SIGN") '(350.0 1.0 0.0) mr))
(ic "manual-result-marked-provisional" (and (= "NEEDS_REVIEW" (bht:get stored "station_status")) (= "1" (bht:get stored "field_manual_control"))))
(ic "manual-source-preserved" (= "MANUAL_CAD" (bht:get (bht:obj-read "HAND") "position_source")))
(bht:obj-write "HAND" (bht:set (bht:obj-read "HAND") "marker_h" "5"))
(ic "edit-number-invalidates-approval" (null (bht:field-marker "HAND" (bht:pt-all))))
(bht:obj-write "HAND" (bht:set (bht:obj-read "HAND") "marker_h" "4"))
(setq he (cdr (assoc 'ent (bht:pt-find "HAND" (bht:pt-all)))))
(entmod (subst '(10 401.0 0.0 0.0) (assoc 10 (entget he)) (entget he)))
(ic "move-invalidates-approval" (null (bht:field-marker "HAND" (bht:pt-all))))
(entmod (subst '(10 400.0 0.0 0.0) (assoc 10 (entget he)) (entget he)))
(ic "revoke-hand" (= "OK" (car (bht:api-field-manual-control "HAND" "0"))))
(ic "revoked-explicit-pair-rejected" (= "LOI" (car (bht:api-field-pair "SIGN" "A" "HAND"))))
(bht:api-field-manual-control "HAND" "1")
(bht:api-field-input-use (cadr (bht:api-field-input-preview)))
(bht:obj-delete "KM")
(setq in 0)
(repeat 25
  (im (strcat "M" (itoa in)) (+ 1000.0 (* in 100.0)) 0.0 (itoa (+ 41 (fix (/ in 10)))) (itoa (rem in 10)))
  (setq in (1+ in)))
(setq snap (cadr (bht:api-field-input-preview)))
(ic "snapshot-longer-than-XRecord-chunk" (> (strlen snap) 1000))
(bht:api-field-input-use snap)
(ic "long-snapshot-roundtrip" (= snap (bht:get (bht:rec-read "FIELD_CHAIN" "BHT_IMPORTED_MARKERS") "input_snapshot")))
(ic "distant-warning-does-not-block-local-segment" (= "OK" (car (bht:api-object-station "SIGN"))))
(im "H9" 99900.0 0.0 "99" "9")
(im "K100" 100000.0 0.0 "100" "")
(bht:obj-write "K100" (bht:set (bht:obj-read "K100") "nhom" "COT_KM"))
(im "H1" 100100.0 0.0 "100" "1")
(ic "new-Km-requires-review" (= "COC_DA_THAY_DOI" (cdr (assoc 'status (bht:field-result nil '(99950.0 2.0 0.0) (bht:pt-all))))))
(bht:api-field-input-use (cadr (bht:api-field-input-preview)))
(setq kr (bht:field-result nil '(99950.0 2.0 0.0) (bht:pt-all)))
(ic "before-Km-uses-H9-to-Km" (and (= "H9" (cdr (assoc 'marker_a kr))) (= "K100" (cdr (assoc 'marker_b kr))) (equal 99950.0 (cdr (assoc 'station kr)) 1e-8)))
(setq kr (bht:field-result nil '(100050.0 2.0 0.0) (bht:pt-all)))
(ic "after-Km-uses-Km-to-H1" (and (= "K100" (cdr (assoc 'marker_a kr))) (= "H1" (cdr (assoc 'marker_b kr))) (equal 100050.0 (cdr (assoc 'station kr)) 1e-8)))
(ic "Km-no-H-needed" (equal 100000.0 (cadr (bht:field-marker "K100" (bht:pt-all))) 1e-8))
(setq kbefore (bht:obj-read "K100"))
(bht:api-object-station "K100")
(ic "Km-record-not-overwritten-by-interpolation" (equal kbefore (bht:obj-read "K100")))
(im "H0" 100003.0 0.0 "100" "0")
(bht:api-field-input-use (cadr (bht:api-field-input-preview)))
(ic "Km-H0-conflict-not-silently-deduplicated" (= "COC_CAN_DOI_CHIEU" (cdr (assoc 'status (bht:field-result nil '(99950.0 2.0 0.0) (bht:pt-all))))))
(bht:obj-delete "H0")
(bht:obj-write "K100" (bht:set (bht:obj-read "K100") "position_source" "MANUAL_CAD"))
(ic "manual-Km-default-excluded" (null (bht:field-marker "K100" (bht:pt-all))))
(ic "manual-Km-approve-without-H" (= "OK" (car (bht:api-field-manual-control "K100" "1"))))
(ic "manual-Km-eligible" (= "MANUAL_CAD" (nth 3 (bht:field-marker "K100" (bht:pt-all)))))
(bht:obj-write "K100" (bht:set (bht:obj-read "K100") "nhom" "COC_TIEU"))
(ic "change-type-invalidates-approval" (not (bht:field-manual-approved (bht:obj-read "K100") (bht:pt-all))))
(bht:obj-write "K100" (bht:set (bht:obj-read "K100") "nhom" "COT_KM"))
(ic "manual-Km-revoke" (= "OK" (car (bht:api-field-manual-control "K100" "0"))))
(ic "manual-Km-revoked-ineligible" (null (bht:field-marker "K100" (bht:pt-all))))
(bht:api-field-manual-control "K100" "1")
(bht:api-field-input-use (cadr (bht:api-field-input-preview)))
(setq kr (bht:field-result nil '(99950.0 2.0 0.0) (bht:pt-all)))
(ic "manual-Km-result-is-reference" (= "1" (cdr (assoc 'manual_control kr))))
(princ (strcat "\nINPUT-FINAL-PASS=" (itoa imported-passes) " INPUT-FINAL-FAIL=" (itoa imported-fails)))
(princ)
