(setq p115-n 0 p115-fail 0)
(defun p115-check (name ok)
  (setq p115-n (1+ p115-n)) (if (not ok) (setq p115-fail (1+ p115-fail)))
  (princ (strcat "\n" (if ok "PASS PRESENTATION115 " "FAIL PRESENTATION115 ") name)))
(defun p115-caption (id / d a e tdata local tb)
  (setq d (entget (m114-insert id))
        a (list (cdr (assoc 10 d)) (abs (cdr (assoc 41 d))) (cdr (assoc 50 d)))
        e (cdr (assoc id (bht:tagged-pairs "TEXT" "BHT_KH" 1))) tdata (entget e)
        local (mapcar '(lambda (v) (/ v (cadr a))) (bht:kh-caption-local (cdr (assoc 11 tdata)) a))
        tb (textbox (list '(0 . "TEXT") (assoc 1 tdata) (assoc 7 tdata) (assoc 40 tdata))))
  (and (equal local '(-0.81 0.0) 1e-7) (= (cdr (assoc 62 tdata)) 2)
       (= (cdr (assoc 72 tdata)) 1) (= (cdr (assoc 73 tdata)) 2)
       (<= (- (caadr tb) (caar tb)) (+ (* 1.28 (cadr a)) 1e-7))
       (<= (cdr (assoc 40 tdata)) (* 0.28 (cadr a)))))
(foreach id '("ML" "MR" "MC")
  (p115-check (strcat "yellow-caption-fits-post-" id) (p115-caption id)))
(bht:obj-write "ML" (bht:set (bht:set (bht:obj-read "ML") "marker_km" "123456") "marker_h" "9"))
(bht:symbol-sync '("ML"))
(p115-check "long-caption-fits-post" (p115-caption "ML"))
(bht:layer "BHT_RTK_TEN" 7)
(bht:regapp "BHT_NHAN")
(setq p115-white (bht:text "H9/123456" '(75.0 90.0 0.0) 0.5 "BHT_RTK_TEN"))
(entmod (append (entget p115-white) (list (bht:lbl-xdata "ML" "TEN" "TAY" '(75.0 90.0 0.0)))))
(setq p115-raw (bht:text "Survey note" '(90.0 90.0 0.0) 0.5 "BHT_RTK_TEN"))
(bht:symbol-sync '("ML"))
(p115-check "remove-duplicate-white-name-only" (and (null (entget p115-white)) (entget p115-raw)))
(bht:lbl-sync-scope 'ALL)
(p115-check "point-label-refresh-does-not-recreate-marker-name"
  (null (vl-some '(lambda (pr) (and (= (car pr) "ML") (= (cadr (bht:xget (cdr pr) "BHT_NHAN")) "TEN")))
    (bht:tagged-pairs "TEXT" "BHT_NHAN" 1))))
(bht:obj-create "SHARED115" '(("nhom" . "KHAC")) '("MR") T)
(bht:lbl-sync-scope 'ALL)
(p115-check "shared-survey-name-preserved"
  (vl-some '(lambda (pr) (and (= (car pr) "MR") (= (cadr (bht:xget (cdr pr) "BHT_NHAN")) "TEN")))
    (bht:tagged-pairs "TEXT" "BHT_NHAN" 1)))

;; Compare automatic placement with a real individual placement at the resulting point.
(defun p115-shape (id / out pr d)
  (foreach pr (bht:tagged-pairs "*" "BHT_KH" 1)
    (if (= (car pr) id)
      (progn (setq d (entget (cdr pr)))
        (setq out (append out (list (vl-remove-if '(lambda (p) (member (car p) '(-1 5 330))) d))))))) out)
(bht:api-symbol-center "R114" "14" "GAP_KHUC")
(setq p115-d (entget (m114-insert "BB")) p115-target (cdr (assoc 10 p115-d))
      p115-before (p115-shape "BB") p115-pick (eval 'bht:kh-pick-target))
(p115-check "bulk-follows-route-at-sign" (equal (cdr (assoc 50 p115-d)) 0.0 1e-7))
(defun bht:kh-pick-target (source cursor) (trans p115-target 0 1))
(bht:kh-place-options "BB" "ELBOW" "ROUTE_PERP" "0")
(set 'bht:kh-pick-target p115-pick)
(p115-check "bulk-and-individual-produce-same-display" (equal p115-before (p115-shape "BB") 1e-6))
(bht:obj-create "TWO115" '(("nhom" . "BIEN_BAO") ("ma_hieu" . "W.209") ("so_tru" . "2") ("route_id" . "R114")) '("ML" "MN") T)
(bht:obj-write "TWO115" (bht:set (bht:obj-read "TWO115") "route_id" "R114"))
(bht:symbol-sync '("TWO115"))
(bht:api-symbol-center "R114" "14" "GAP_KHUC")
(setq p115-target (cdr (assoc 10 (entget (m114-insert "TWO115")))) p115-before (p115-shape "TWO115"))
(defun bht:kh-pick-target (source cursor) (trans p115-target 0 1))
(bht:kh-place-options "TWO115" "ELBOW" "ROUTE_PERP" "0")
(set 'bht:kh-pick-target p115-pick)
(p115-check "two-post-bulk-matches-individual" (equal p115-before (p115-shape "TWO115") 1e-6))
(bht:obj-create "CURVE115" '(("nhom" . "BIEN_BAO") ("ma_hieu" . "W.209") ("route_id" . "ARC114")) '("MC") T)
(bht:obj-write "CURVE115" (bht:set (bht:obj-read "CURVE115") "route_id" "ARC114"))
(bht:symbol-sync '("CURVE115"))
(bht:api-symbol-center "ARC114" "10" "GAP_KHUC")
(setq p115-angle (cdr (assoc 50 (entget (m114-insert "CURVE115")))))
(p115-check "curved-reversed-route-uses-local-tangent"
  (and (equal (cos p115-angle) (- (/ 1.0 (sqrt 2.0))) 1e-6)
       (equal (sin p115-angle) (/ 1.0 (sqrt 2.0)) 1e-6)))
(bht:api-symbol-center "R114" "14" "GAP_KHUC")
(p115-check "bulk-caption-still-inside-marker" (p115-caption "ML"))
(p115-check "survey-coordinates-unchanged" (equal m114-points (vl-remove-if '(lambda (p) (= (car p) "MC")) (bht:pt-all))))
(princ (strcat "\nPRESENTATION115-CHECKS=" (itoa p115-n) " FAIL=" (itoa p115-fail))) (princ)
