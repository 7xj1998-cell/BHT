(light-check "signal-group-code" (= (bht:group-code "10") "DEN_TH"))
(light-check "lighting-group-code" (= (bht:group-code "9") "DEN_CS"))
(light-check "legacy-light-group-retained" (= (bht:group-code "6") "DEN"))
(light-check "signal-survey-classification" (= (bht:classify "dentinhieu.vuon6m1") "DEN_TH"))
(foreach group '("DEN_CS" "DEN_TH")
 (setq model (if (= group "DEN_CS") "BHT_LIGHT_DEN_CS_DON_MB_*" "BHT_LIGHT_DEN_TIN_HIEU_3_MAU_*")
       light-row (tblnext "BLOCK" T) selected nil)
 (while light-row (if (wcmatch (cdr (assoc 2 light-row)) model) (setq selected (cdr (assoc 2 light-row)))) (setq light-row (tblnext "BLOCK")))
 (setq oid (strcat "LIGHT-" group))
 (bht:obj-create oid (list (cons "nhom" group) (cons "custom_block" selected)) '("LIGHT-PT") T)
 (bht:kh-free-apply oid '(110.0 105.0 0.0) 0.7 nil)
 (setq inserted (cdr (assoc oid (bht:tagged-pairs "INSERT" "BHT_KH" 1))))
 (light-check (strcat group "-saved-group-and-exact-model") (and (= (bht:get (bht:obj-read oid) "nhom") group) (= (cdr (assoc 2 (entget inserted))) selected)))
 (light-check (strcat group "-RTK-unchanged") (equal light-before (entget light-p '("BHT_PT")))))
(bht:obj-create "MISSING-QA" '(("nhom" . "BIEN_BAO") ("tinh_trang" . "Mất mặt biển, còn trụ") ("so_tru" . "1") ("ma_hieu" . "W.207a") ("mat" . "W.207a") ("mat" . "S.501")) '("LIGHT-PT") T)
(bht:kh-free-apply "MISSING-QA" '(112.0 100.0 0.0) 0.7 nil)
(setq mi (cdr (assoc "MISSING-QA" (bht:tagged-pairs "INSERT" "BHT_KH" 1))) mb (cdr (assoc 2 (entget mi))))
(light-check "missing-face-no-question-mark-block" (= mb (BHTSIGNPORTABLE "BHT_MISSING_FACE_V0660_1")))
(light-check "missing-face-no-external-label" (= (bht:kh-label "MISSING-QA" (bht:obj-read "MISSING-QA")) ""))
(light-check "missing-face-retains-known-code" (= (bht:get (bht:obj-read "MISSING-QA") "ma_hieu") "W.207a"))
(light-check "missing-face-no-stale-extra-labels" (= (length (vl-remove-if-not '(lambda (p) (= (car p) "MISSING-QA")) (bht:tagged-pairs "TEXT" "BHT_KH" 1))) 0))
(setq missing-texts nil me (entnext (tblobjname "BLOCK" mb)))
(while (and me (/= (cdr (assoc 0 (entget me))) "ENDBLK"))
  (if (= (cdr (assoc 0 (entget me))) "TEXT") (setq missing-texts (cons (entget me) missing-texts)))
  (setq me (entnext me)))
(light-check "missing-face-one-centered-caption" (and (= (length missing-texts) 1)
  (= (cdr (assoc 1 (car missing-texts))) (bht:cad-text "TRỤ MẤT BIỂN" (cdr (assoc 7 (car missing-texts)))))
  (equal (cdr (assoc 11 (car missing-texts))) '(0.0 1.2 0.0) 1e-8)))
(setq missing-width (textbox (car missing-texts)))
(light-check "missing-caption-fits-frame" (< (- (caadr missing-width) (caar missing-width)) 2.2))
(setq missing-before (entget mi))
(bht:block "BHT_MISSING_FACE_V0646_1" (list (bht:line-g '(0.0 0.0 0.0) '(0.0 1.8 0.0))))
(entmod (bht:dxf-put (entget mi) 2 "BHT_MISSING_FACE_V0646_1"))

(setq missing-old-label (entmakex (append '((0 . "TEXT") (8 . "BHT_NHAN") (10 112.0 100.0 0.0) (40 . 0.35) (1 . "Trụ mất mặt biển"))
  (list (bht:kh-xdata-txt "MISSING-QA" "TU_DONG" '(112.0 100.0 0.0))))))
(bht:symbol-sync '("MISSING-QA"))
(light-check "missing-old-label-removed" (null (entget missing-old-label)))
(light-check "missing-update-keeps-placement" (equal missing-before (entget mi)))
(bht:obj-write "MISSING-QA" (bht:set (bht:obj-read "MISSING-QA") "so_tru" "2"))
(bht:symbol-sync '("MISSING-QA"))
(light-check "missing-two-post-frame" (= (cdr (assoc 2 (entget mi))) (BHTSIGNPORTABLE "BHT_MISSING_FACE_V0660_2")))
(light-check "missing-two-post-no-label" (null (assoc "MISSING-QA" (bht:tagged-pairs "TEXT" "BHT_KH" 1))))
(bht:obj-write "MISSING-QA" (bht:set (bht:obj-read "MISSING-QA") "tinh_trang" "Tốt"))
(bht:symbol-sync '("MISSING-QA"))
(light-check "restore-face-uses-retained-code" (/= (cdr (assoc 2 (entget mi))) mb))
(light-check "missing-face-keeps-RTK" (equal light-before (entget light-p '("BHT_PT"))))
