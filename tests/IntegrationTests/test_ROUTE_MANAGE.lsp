(setq manage-fails 0)
(defun manage-check (n ok) (if (not ok) (setq manage-fails (1+ manage-fails))) (princ (strcat "\n" (if ok "PASS MANAGE " "FAIL MANAGE ") n)))
(setq manage-old (bht:route-read "HEAD-ROUTE") manage-geom (entget heading-pl))
(manage-check "duplicate-id-does-not-overwrite" (and (not (car (bht:route-create "HEAD-ROUTE" heading-pl "KHAC" 50.0 0.0 nil "QA"))) (equal manage-old (bht:route-read "HEAD-ROUTE"))))
(manage-check "negative-extrapolation-rejected" (not (car (bht:route-create "BAD" heading-pl "KHAC" 50.0 -1.0 nil "QA"))))
(bht:obj-write "HEAD-A" (bht:set (bht:obj-read "HEAD-A") "route_id" "HEAD-ROUTE"))
(bht:kh-heading-apply '("HEAD-A") "ROUTE_PERP" "HEAD-ROUTE" nil)
(setq manage-angle (heading-angle "HEAD-A"))
(manage-check "rename-route" (car (bht:route-edit "HEAD-ROUTE" "RENAMED" "TIM_DUONG" 150.0 20.0)))
(manage-check "rename-updates-both-links" (and (= (bht:get (bht:obj-read "HEAD-A") "route_id") "RENAMED") (= (bht:get (bht:obj-read "HEAD-A") "sign_heading_route") "RENAMED") (null (bht:route-read "HEAD-ROUTE"))))
(manage-check "edit-invalidates-derived-station" (and (= (bht:get (bht:obj-read "HEAD-A") "station_status") "STALE") (= (bht:get (bht:obj-read "HEAD-A") "ly_trinh_m") "")))
(manage-check "rename-collision-rejected" (not (car (bht:route-edit "RENAMED" "HEAD-ARC" "TIM_DUONG" 100.0 0.0))))
(setq *bht-route-selected* "RENAMED")
(manage-check "selected-route-used-once" (and (= (bht:ask-route) "RENAMED") (null *bht-route-selected*)))
(manage-check "delete-route" (car (bht:route-delete "RENAMED")))
(manage-check "delete-keeps-source-geometry-and-RTK" (and (equal manage-geom (entget heading-pl)) (equal heading-rtk (list (entget heading-p1 '("BHT_PT")) (entget heading-p2 '("BHT_PT"))))))
(manage-check "delete-clears-links-keeps-angle-mode" (and (null (bht:route-read "RENAMED")) (= (bht:get (bht:obj-read "HEAD-A") "route_id") "") (= (bht:get (bht:obj-read "HEAD-A") "sign_heading_mode") "FIXED")))
(bht:symbol-sync-ex '("HEAD-A") nil)
(manage-check "delete-retains-perpendicular-heading-on-refresh" (heading-same-angle manage-angle (heading-angle "HEAD-A")))
(bht:route-create "REPLACE" heading-pl "TIM_DUONG" 100.0 0.0 nil "QA")
(bht:route-add-mark "REPLACE" 0.0 1000.0 1000.0 "QA" "")
(setq manage-new (entmakex '((0 . "LWPOLYLINE") (100 . "AcDbEntity") (100 . "AcDbPolyline") (90 . 2) (70 . 0) (10 20.0 20.0) (10 20.0 40.0))))
(manage-check "same-geometry-keeps-marks" (and (not (car (bht:route-replace "REPLACE" heading-pl))) (= (length (bht:route-marks (bht:route-read "REPLACE"))) 1)))
(manage-check "replace-source" (car (bht:route-replace "REPLACE" manage-new)))
(manage-check "replace-resets-controls-and-geometry" (and (null (bht:route-marks (bht:route-read "REPLACE"))) (= (bht:get (bht:route-read "REPLACE") "handle") (cdr (assoc 5 (entget manage-new)))) (> (bht:route-revision (bht:route-read "REPLACE")) 1)))
(princ (strcat "\nMANAGE-FAIL=" (itoa manage-fails)))
