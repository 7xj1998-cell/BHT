(setq q124-count 0 q124-fail 0)
(defun q124-check (name ok) (setq q124-count (1+ q124-count)) (if (not ok) (setq q124-fail (1+ q124-fail))) (princ (strcat "\n" (if ok "PASS SELECTION124 " "FAIL SELECTION124 ") name)))
(setq q124-before (bht:obj-read "OBJ-000058"))
(q124-check "real-input-station-valid-but-wrong-road-side" (and (= (bht:get q124-before "phia_duong") "PHAI") (= (bht:get q124-before "ly_trinh_m") "50871.602") (= (bht:get q124-before "doan") "")))
(setq q124-result (bht:seg-refresh-record q124-before))
(q124-check "wrong-road-side-not-silently-overridden" (and (= (bht:get q124-result "gan_doan_pp") "KHAC_PHIA_DUONG") (= (bht:get q124-result "doan") "")))
(setq q124-left (bht:set q124-before "phia_duong" "TRAI"))
(setq q124-result (bht:seg-refresh-record q124-left))
(q124-check "correct-road-side-assigns-segment-and-package" (and (= (bht:get q124-result "doan") "DOAN_10") (= (bht:get q124-result "goi") "GOI_03")))
(setq q124-result (bht:seg-refresh-record (bht:set (bht:set q124-left "loai_tuyen" "TIM_RANH") "phia_tuyen" "PHAI")))
(q124-check "ditch-side-does-not-reject-road-side" (= (bht:get q124-result "doan") "DOAN_10"))
(setq q124-seg (bht:rec-read "SEG" "DOAN_10"))
(bht:rec-write "SEG" "DOAN_10" (bht:set q124-seg "route_id" "OTHER_ROUTE"))
(q124-check "different-route-not-assigned-by-Km-alone" (= (bht:get (bht:seg-refresh-record q124-left) "doan") ""))
(bht:rec-write "SEG" "DOAN_10" q124-seg)
(bht:rec-write "SEG" "DUPLICATE" (bht:set q124-seg "segment_id" "DUPLICATE"))
(q124-check "overlap-requires-choice" (= (bht:get (bht:seg-refresh-record q124-left) "gan_doan_pp") "NHIEU_DOAN"))
(bht:rec-delete "SEG" "DUPLICATE")
(bht:obj-write "OBJ-000058" q124-left)
(setq q124-result (bht:station-one "OBJ-000058"))
(q124-check "real-station-one-refreshes-assignment" (and (not (eq (car q124-result) 'LOI)) (= (bht:get (bht:obj-read "OBJ-000058") "doan") "DOAN_10")))
(bht:obj-write "OBJ-000058" q124-before)
(setq q124-result (bht:assign-manual "OBJ-000058" "DOAN_10"))
(q124-check "explicit-manual-override-allowed" (and (car q124-result) (= (bht:get (bht:obj-read "OBJ-000058") "gan_doan_pp") "THU_CONG")))
(bht:station-one "OBJ-000058")
(q124-check "recalculation-preserves-manual-choice" (= (bht:get (bht:obj-read "OBJ-000058") "doan") "DOAN_10"))
(bht:obj-write "OBJ-000058" q124-left)
(setq q124-result (bht:route-recalculate "TIMRANHD10"))
(q124-check "real-route-recalculation-fills-automatic-segment" (and (not (eq (car q124-result) 'LOI)) (= (bht:get (bht:obj-read "OBJ-000058") "doan") "DOAN_10")))
(q124-check "real-route-recalculation-retains-other-manual-choice" (and (= (bht:get (bht:obj-read "OBJ-000060") "doan") "DOAN_10") (= (bht:get (bht:obj-read "OBJ-000060") "gan_doan_pp") "THU_CONG")))
(bht:obj-write "OBJ-000058" q124-before)
(princ (strcat "\nSELECTION124-CHECKS=" (itoa q124-count) " FAIL=" (itoa q124-fail))) (princ)
