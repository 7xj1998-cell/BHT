(setq l108-n 0 l108-fail 0)
(defun l108-check (name ok)
  (setq l108-n (1+ l108-n)) (if (not ok) (setq l108-fail (1+ l108-fail)))
  (princ (strcat "\n" (if ok "PASS LABEL108 " "FAIL LABEL108 ") name)))
(defun l108-labels (id)
  (mapcar 'cdr (vl-remove-if-not '(lambda (pr) (= (car pr) id)) (bht:tagged-pairs "TEXT" "BHT_KH" 1))))
(defun l108-below-p (title station rows / a b p q delta h rot)
  (setq a (entget title) b (entget station) p (cdr (assoc 11 a)) q (cdr (assoc 11 b))
        delta (mapcar '- q p) h (cdr (assoc 40 a)) rot (cdr (assoc 50 a)))
  (and (equal (+ (* (car delta) (cos rot)) (* (cadr delta) (sin rot))) 0.0 1e-6)
       (equal (+ (* (- (car delta)) (sin rot)) (* (cadr delta) (cos rot))) (- (* rows h 1.5)) 1e-6)
       (equal (cdr (assoc 50 a)) (cdr (assoc 50 b)) 1e-8)
       (equal (cdr (assoc 40 a)) (cdr (assoc 40 b)) 1e-8)
       (= (cdr (assoc 7 a)) (cdr (assoc 7 b)))))
(setq p108 (entmakex '((0 . "POINT") (10 10.0 10.0 0.0))))
(bht:pt-write-xdata p108 "PT108" "QA" "1" "108" 10.0 10.0 0.0 "BIEN_BAO" "QA" "" "")
(bht:obj-create "SIGN108" '(("nhom" . "BIEN_BAO") ("ma_hieu" . "W.202a") ("so_tru" . "1") ("ly_trinh_km" . "Km38+966.96") ("ly_trinh_m" . "38966.960")) '("PT108") T)
(bht:obj-write "SIGN108" (bht:set (bht:set (bht:obj-read "SIGN108") "ly_trinh_km" "Km38+966.96") "ly_trinh_m" "38966.960"))
(setq points108 (bht:pt-all) records108 (bht:rec-all "OBJ"))
(foreach angle108 '(0.0 0.4 1.570796326795 3.14159265359 5.2)
  (bht:kh-free-apply "SIGN108" '(14.0 16.0 0.0) angle108 nil)
  (setq labels108 (l108-labels "SIGN108") title108 (car (vl-remove-if 'bht:kh-extra-label-p labels108)) station108 (car (vl-remove-if-not 'bht:kh-station-label-p labels108)))
  (l108-check (strcat "two-editable-TEXT-lines-" (rtos angle108 2 2)) (= (length labels108) 2))
  (l108-check (strcat "name-and-chainage-separated-" (rtos angle108 2 2))
    (and (= "W.202a" (cdr (assoc 1 (entget title108)))) (= "Km38+966.96" (cdr (assoc 1 (entget station108))))))
  (l108-check (strcat "chainage-below-name-same-font-size-angle-" (rtos angle108 2 2)) (l108-below-p title108 station108 1)))
;; Migrate an old single-line label without moving the sign or changing survey data.
(bht:block "BHT_LEGACY_DEN108" (list (bht:line-g '(0.0 0.0 0.0) '(1.0 1.0 0.0))))
(bht:obj-create "LIGHT108" '(("nhom" . "DEN_TH") ("custom_block" . "BHT_LEGACY_DEN108")) '("PT108") T)
(setq light108 (bht:insert "BHT_LEGACY_DEN108" '(30.0 30.0 0.0) "BHT_KYHIEU" 1.4))
(entmod (append (entget light108) (list (bht:kh-xdata-ins "LIGHT108" "TAY" '(30.0 30.0 0.0) 0.0 1.4))))
(setq light108-before (entget light108 '("BHT_KH")))
(entdel station108)
(entmod (bht:dxf-put (entget title108) 1 "W.202a  Km38+966.96"))
(setq insert108 (cdr (assoc "SIGN108" (bht:tagged-pairs "INSERT" "BHT_KH" 1))) geometry108 (entget insert108) records108 (bht:rec-all "OBJ"))
(bht:meta-set "symbol_build" "1.0.7")
(l108-check "upgrade-API-success" (= "OK" (car (bht:api-symbol-upgrade))))
(setq labels108 (l108-labels "SIGN108") station108 (car (vl-remove-if-not 'bht:kh-station-label-p labels108)))
(l108-check "old-single-line-migrated" (and (= (length labels108) 2) (= "W.202a" (cdr (assoc 1 (entget title108)))) (l108-below-p title108 station108 1)))
(l108-check "upgrade-keeps-insert-and-records" (and (equal geometry108 (entget insert108)) (equal points108 (bht:pt-all)) (equal records108 (bht:rec-all "OBJ"))))
(l108-check "sign-template-upgrade-does-not-replace-light-block" (equal light108-before (entget light108 '("BHT_KH"))))
(setq text108 (mapcar '(lambda (e) (entget e '("BHT_KH"))) labels108))
(bht:api-symbol-sync "SIGN108")
(l108-check "update-idempotent-no-duplicates" (equal text108 (mapcar '(lambda (e) (entget e '("BHT_KH"))) (l108-labels "SIGN108"))))
(bht:obj-write "SIGN108" (bht:set (bht:obj-read "SIGN108") "ly_trinh_km" "Km40+100.00"))
(bht:api-symbol-sync "SIGN108")
(l108-check "chainage-updates-existing-line" (and (= (length (l108-labels "SIGN108")) 2) (= "Km40+100.00" (cdr (assoc 1 (entget station108))))))
(bht:obj-write "SIGN108" (bht:set (bht:obj-read "SIGN108") "ly_trinh_km" ""))
(bht:api-symbol-sync "SIGN108")
(l108-check "empty-chainage-removes-only-second-line" (and (= (length (l108-labels "SIGN108")) 1) (entget title108) (null (entget station108))))
(bht:obj-write "SIGN108" (bht:set (bht:obj-read "SIGN108") "ly_trinh_km" "Km38+966.96"))
(bht:obj-create "MULTI108" '(("nhom" . "BIEN_BAO") ("ma_hieu" . "P.127-80") ("so_mat" . "2") ("mat" . "P.127-80") ("mat" . "S.505a@8") ("ly_trinh_km" . "Km40+500.00")) '("PT108") T)
(bht:obj-write "MULTI108" (bht:set (bht:obj-read "MULTI108") "ly_trinh_km" "Km40+500.00"))
(bht:kh-free-apply "MULTI108" '(20.0 20.0 0.0) 0.6 nil)
(setq labels108 (l108-labels "MULTI108") title108 (car (vl-remove-if 'bht:kh-extra-label-p labels108)) station108 (car (vl-remove-if-not 'bht:kh-station-label-p labels108)))
(l108-check "multi-face-chainage-after-all-names" (and (= 3 (length labels108)) (l108-below-p title108 station108 2)))
(bht:api-sign-scale "2" "0.75")
(setq labels108 (l108-labels "MULTI108") title108 (car (vl-remove-if 'bht:kh-extra-label-p labels108)) station108 (car (vl-remove-if-not 'bht:kh-station-label-p labels108)))
(l108-check "independent-label-scale-keeps-stack" (and (= 3 (length labels108)) (l108-below-p title108 station108 2)))
(setq before108 (mapcar 'entget labels108)) (bht:api-sign-scale "2" "0.75")
(l108-check "repeat-scale-no-drift-or-duplicates" (equal before108 (mapcar 'entget (l108-labels "MULTI108"))))
(bht:obj-write "MULTI108" (bht:set (bht:set-all (bht:obj-read "MULTI108") "mat" '("P.127-80")) "so_mat" "1"))
(bht:api-symbol-sync "MULTI108")
(setq labels108 (l108-labels "MULTI108") title108 (car (vl-remove-if 'bht:kh-extra-label-p labels108)) station108 (car (vl-remove-if-not 'bht:kh-station-label-p labels108)))
(l108-check "removed-face-keeps-chainage-under-remaining-name" (and (= 2 (length labels108)) (l108-below-p title108 station108 1)))
(l108-check "survey-and-chainage-not-recalculated" (and (equal points108 (bht:pt-all)) (= "38966.960" (bht:get (bht:obj-read "SIGN108") "ly_trinh_m"))))
;; Leave a two-face example in the saved review drawing.
(bht:obj-write "MULTI108" (bht:set (bht:set-all (bht:obj-read "MULTI108") "mat" '("P.127-80" "S.505a@8")) "so_mat" "2"))
(bht:api-symbol-sync "MULTI108")
(princ (strcat "\nLABEL108-CHECKS=" (itoa l108-n) " FAIL=" (itoa l108-fail))) (princ)
