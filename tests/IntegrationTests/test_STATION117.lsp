(setq s117-fails 0 s117-checks 0)
(defun s117-check (name ok)
  (setq s117-checks (1+ s117-checks))
  (if (not ok) (setq s117-fails (1+ s117-fails)))
  (princ (strcat "\n" (if ok "PASS STATION117 " "FAIL STATION117 ") name)))
(defun s117-point (id x y / e)
  (setq e (entmakex (list '(0 . "POINT") (cons 10 (list x y 0.0)))))
  (bht:pt-write-xdata e id "QA" "1" "1" y x 0.0 "BIEN_BAO" "QA" "" "") e)
(defun s117-sign (id pt / fields rec)
  (setq fields '(("nhom" . "BIEN_BAO") ("ma_hieu" . "W.207a") ("ly_trinh_m" . "42000") ("ly_trinh_km" . "Km42+000.00")
    ("station_source" . "FIELD_MARKERS") ("field_chain_id" . "OLD") ("field_pair_a" . "C1") ("field_pair_b" . "C2")
    ("doan" . "OLD-SEG") ("goi" . "OLD-PACK")))
  (bht:obj-create id fields (list pt) T)
  (setq rec (bht:obj-read id))
  (foreach pair fields (setq rec (bht:set rec (car pair) (cdr pair))))
  (bht:obj-write id rec))
(defun s117-snapshot () (list (bht:rec-all "OBJ") (bht:rec-read "META" "CONFIG") (bht:rec-all "ROUTE")))
(setq s117-line (entmakex '((0 . "LWPOLYLINE") (100 . "AcDbEntity") (100 . "AcDbPolyline") (90 . 2) (70 . 0) (10 0.0 0.0) (10 1821.67 0.0))))
(bht:route-create "NEW-TDT" s117-line "TIM_DUONG" 100.0 50.0 nil "TDT fixture")
(bht:route-add-mark "NEW-TDT" 591.450 49103.28 49103.28 "TDT_STAKES A" "")
(bht:route-add-mark "NEW-TDT" 749.232 49265.73 49265.73 "TDT_STAKES B" "")
(bht:route-add-mark "NEW-TDT" 777.663 49294.25 49294.25 "TDT_STAKES C" "")
(foreach row '(("C1" "PC1" 2.826 48 5) ("C2" "PC2" 587.368 49 1) ("C3" "PC3" 688.450 49 2) ("C4" "PC4" 987.442 49 5))
  (s117-point (cadr row) (nth 2 row) 3.0)
  (bht:obj-create (car row) (list '("nhom" . "COC_TIEU") (cons "marker_km" (itoa (nth 3 row))) (cons "marker_h" (itoa (nth 4 row)))) (list (cadr row)) T))
(setq s117-controls (bht:route-object-controls (bht:route-read "NEW-TDT")))
(s117-check "three-TDT-controls-no-four-imported-controls" (and (= 3 (length (car s117-controls))) (null (cadr s117-controls))))
(setq s117-no-tdt (bht:set-all (bht:set (bht:route-read "NEW-TDT") "station_source" "TDT_STAKES") "moc" nil))
(s117-check "missing-TDT-controls-never-fall-back-to-imported-captions" (null (car (bht:route-object-controls s117-no-tdt))))
(setq s117-standard (bht:set-all (bht:set (bht:set s117-no-tdt "nguon" "Polyline") "station_source" "CONTROL_POINTS") "moc" nil))
(s117-check "ordinary-route-still-uses-numbered-markers" (= 4 (length (car (bht:route-object-controls s117-standard)))))
(s117-point "TARGET-P" 650.0 2.0) (s117-sign "TARGET" "TARGET-P")
(s117-point "EARLY-P" 74.0 2.0) (s117-sign "EARLY" "EARLY-P")
(s117-point "FAR-P" 650.0 200.0) (s117-sign "FAR" "FAR-P")
(s117-point "LATE-P" 900.0 2.0) (s117-sign "LATE" "LATE-P")
(s117-point "MISSING-P" 650.0 2.0) (s117-sign "MISSING" "MISSING-P")
(bht:rec-write "OBJ" "MISSING" (bht:set-all (bht:obj-read "MISSING") "pt" '("NO-SUCH-POINT")))
(setq s117-oldline (entmakex '((0 . "LWPOLYLINE") (100 . "AcDbEntity") (100 . "AcDbPolyline") (90 . 2) (70 . 0) (10 0.0 2.0) (10 1821.67 2.0))))
(bht:route-create "OLD" s117-oldline "TIM_DUONG" 100.0 50.0 nil "Old imported route")
(bht:route-add-mark "OLD" 0.0 42000.0 42000.0 "old" "") (bht:route-add-mark "OLD" 1821.67 43821.67 43821.67 "old" "")
(bht:meta-set "station_method" "FIELD_MARKERS") (bht:meta-set "field_active_chain" "OLD")
(setq s117-before (s117-snapshot) s117-survey (mapcar '(lambda (p) (entget (bht:pv (cdr p) 'ent) '("*"))) (bht:pt-all))
      s117-geometry (entget s117-line) s117-marker-records (mapcar 'bht:obj-read '("C1" "C2" "C3" "C4")))
(s117-check "preview-does-not-change-mode-records" (and (= 1 (nth 2 (bht:route-recalculate-plan "NEW-TDT"))) (equal s117-before (s117-snapshot))))
(s117-check "missing-route-rejected-before-write" (and (eq (car (bht:route-recalculate "ABSENT")) 'LOI) (equal s117-before (s117-snapshot))))
(setq s117-original-route (bht:route-read "NEW-TDT"))
(bht:route-write "NEW-TDT" s117-no-tdt)
(s117-check "missing-control-rejects-without-clearing-old-stations" (and (eq (car (bht:route-recalculate "NEW-TDT")) 'LOI) (= "42000" (bht:get (bht:obj-read "TARGET") "ly_trinh_m"))))
(bht:route-write "NEW-TDT" s117-original-route)
(setq s117-save-write bht:obj-write s117-write-count 0)
(defun bht:obj-write (id rec)
  (setq s117-write-count (1+ s117-write-count))
  (if (= s117-write-count 2) nil (s117-save-write id rec)))
(setq s117-fault (vl-catch-all-apply 'bht:route-recalculate '("NEW-TDT")))
(setq bht:obj-write s117-save-write)
(princ (strcat "\nSTATION117-FAULT=" (if (vl-catch-all-error-p s117-fault) (vl-catch-all-error-message s117-fault) (vl-princ-to-string s117-fault))))
(s117-check "failed-write-rolls-back-every-record-and-method" (and (not (vl-catch-all-error-p s117-fault)) (eq (car s117-fault) 'LOI) (equal s117-before (s117-snapshot))))
(setq s117-result (bht:route-recalculate "NEW-TDT") s117-target (bht:obj-read "TARGET")
      s117-expected (+ 49103.28 (* (- 650.0 591.450) (/ (- 49265.73 49103.28) (- 749.232 591.450)))))
(s117-check "selected-route-overrides-closer-old-route" (and (= (bht:get s117-target "route_id") "NEW-TDT") (equal (bht:num (bht:get s117-target "ly_trinh_m")) s117-expected 0.001)))
(s117-check "stale-field-method-and-pairs-replaced" (and (= "ROUTE" (bht:meta "station_method" "")) (= "NEW-TDT" (bht:meta "station_active_route" "")) (= "" (bht:get s117-target "field_pair_a")) (= "" (bht:get s117-target "field_chain_id"))))
(s117-check "old-segment-assignment-invalidated" (and (= "" (bht:get s117-target "doan")) (= "" (bht:get s117-target "goi"))))
(s117-check "early-late-far-missing-stations-cleared-and-flagged" (vl-every '(lambda (id / rec) (setq rec (bht:obj-read id)) (and (= "" (bht:get rec "ly_trinh_m")) (/= "VALID" (bht:get rec "station_status")))) '("EARLY" "LATE" "FAR" "MISSING")))
(s117-check "numbered-markers-are-preserved-observations" (equal s117-marker-records (mapcar 'bht:obj-read '("C1" "C2" "C3" "C4"))))
(s117-check "survey-and-alignment-unchanged" (and (equal s117-survey (mapcar '(lambda (p) (entget (bht:pv (cdr p) 'ent) '("*"))) (bht:pt-all))) (equal s117-geometry (entget s117-line))))
(s117-check "single-object-button-now-uses-active-new-route" (and (= "OK" (car (bht:api-object-station "TARGET"))) (= "NEW-TDT" (bht:get (bht:obj-read "TARGET") "route_id"))))
(s117-check "diagnostic-explains-control-source" (vl-some '(lambda (s) (vl-string-search "không dùng số Km/H" s)) (bht:route-diag-lines "NEW-TDT")))
(setq s117-moved (subst '(10 1830.0 0.0) '(10 1821.67 0.0) (entget s117-line)))
(entmod s117-moved)
(s117-check "changed-alignment-requires-control-review" (eq (car (bht:route-recalculate "NEW-TDT")) 'LOI))
(entmod s117-geometry)
(bht:route-edit "NEW-TDT" "RENAMED-TDT" "TIM_DUONG" 100.0 50.0)
(s117-check "renaming-active-route-updates-station-selection" (= "RENAMED-TDT" (bht:meta "station_active_route" "")))
(bht:route-edit "RENAMED-TDT" "NEW-TDT" "TIM_DUONG" 100.0 50.0)
(bht:route-add-mark "NEW-TDT" 0.0 48511.83 48511.83 "Mốc bổ sung xác nhận" "fixture")
(bht:route-recalculate "NEW-TDT")
(s117-check "adding-earlier-confirmed-control-enables-earlier-station" (equal 48585.83 (bht:num (bht:get (bht:obj-read "EARLY") "ly_trinh_m")) 0.001))
(bht:route-del-mark "NEW-TDT" 0)
(bht:route-recalculate "NEW-TDT")
(setq s117-arc (entmakex '((0 . "LWPOLYLINE") (100 . "AcDbEntity") (100 . "AcDbPolyline") (90 . 2) (70 . 0) (10 0.0 3000.0) (42 . 1.0) (10 200.0 3000.0)))
      s117-arc-len (bht:curve-length s117-arc))
(bht:route-create "ARC" s117-arc "TIM_DUONG" 100.0 0.0 nil "TDT arc fixture")
(bht:route-set-start-dir "ARC" (vlax-curve-getEndPoint s117-arc) -1)
(bht:route-add-mark "ARC" 0.0 50000.0 50000.0 "TDT_STAKES A" "")
(bht:route-add-mark "ARC" s117-arc-len (+ 50000.0 s117-arc-len) (+ 50000.0 s117-arc-len) "TDT_STAKES B" "")
(setq s117-arc-point (vlax-curve-getPointAtDist s117-arc (/ s117-arc-len 4.0)))
(s117-point "ARC-P" (car s117-arc-point) (cadr s117-arc-point)) (s117-sign "ARC-SIGN" "ARC-P")
(s117-check "reversed-curved-route-uses-arc-length-not-chord" (and (not (eq (car (bht:route-recalculate "ARC")) 'LOI))
  (equal (+ 50000.0 (* s117-arc-len 0.75)) (bht:num (bht:get (bht:obj-read "ARC-SIGN") "ly_trinh_m")) 0.001)))
(bht:obj-delete "ARC-SIGN") (bht:route-delete "ARC")
(s117-check "deleted-active-route-does-not-fall-back-to-old-route" (= "CHUA_CO_TUYEN" (cdr (assoc 'status (bht:station '(650.0 2.0 0.0))))))
(bht:route-recalculate "NEW-TDT")
(setq s117-final (s117-snapshot))
(princ (strcat "\nSTATION117-CHECKS=" (itoa s117-checks) " FAIL=" (itoa s117-fails)))
(princ)
