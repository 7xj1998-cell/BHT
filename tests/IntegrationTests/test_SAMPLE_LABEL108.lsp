(setq sl108-points (bht:pt-all) sl108-records (bht:rec-all "OBJ") sl108-routes (bht:rec-all "ROUTE") sl108-chains (bht:rec-all "FIELD_CHAIN")
      sl108-inserts (mapcar '(lambda (pr / d) (setq d (entget (cdr pr))) (list (car pr) (assoc 10 d) (assoc 41 d) (assoc 42 d) (assoc 43 d) (assoc 50 d))) (bht:tagged-pairs "INSERT" "BHT_KH" 1)))
(bht:meta-set "symbol_build" "1.0.7")
(setq sl108-start (getvar "MILLISECS") sl108-result (bht:api-symbol-upgrade) sl108-ms (- (getvar "MILLISECS") sl108-start))
(princ sl108-result)
(princ (if (= "OK" (car sl108-result)) "\nSAMPLE-LABEL108-UPGRADE-PASS" "\nSAMPLE-LABEL108-UPGRADE-FAIL"))
(princ (if (and (equal sl108-points (bht:pt-all)) (equal sl108-records (bht:rec-all "OBJ")) (equal sl108-routes (bht:rec-all "ROUTE")) (equal sl108-chains (bht:rec-all "FIELD_CHAIN"))
  (equal sl108-inserts (mapcar '(lambda (pr / d) (setq d (entget (cdr pr))) (list (car pr) (assoc 10 d) (assoc 41 d) (assoc 42 d) (assoc 43 d) (assoc 50 d))) (bht:tagged-pairs "INSERT" "BHT_KH" 1)))) "\nSAMPLE-LABEL108-PRESERVE-PASS" "\nSAMPLE-LABEL108-PRESERVE-FAIL"))
(foreach row sl108-records
  (if (not (equal (cdr row) (bht:obj-read (car row))))
    (progn (princ (strcat "\nRECORD-DIFF " (car row)))
      (foreach kv (cdr row) (if (not (= (cdr kv) (bht:get (bht:obj-read (car row)) (car kv)))) (princ (list kv (cons (car kv) (bht:get (bht:obj-read (car row)) (car kv))))))))))
(foreach row sl108-inserts
  (setq ent (cdr (assoc (car row) (bht:tagged-pairs "INSERT" "BHT_KH" 1))) d (entget ent)
        current (list (car row) (assoc 10 d) (assoc 41 d) (assoc 42 d) (assoc 43 d) (assoc 50 d)))
  (if (not (equal row current)) (progn (princ "\nINSERT-DIFF ") (princ (list row current)))))
(setq sl108-count 0 sl108-bad 0)
(foreach pair sl108-records
  (setq id (car pair) rec (cdr pair))
  (if (and (bht:kh-fillable-p rec) (/= (bht:get rec "ly_trinh_km") "") (/= (bht:kh-label id rec) "") (assoc id (bht:tagged-pairs "INSERT" "BHT_KH" 1)))
    (progn
      (setq sl108-count (1+ sl108-count) labels (mapcar 'cdr (vl-remove-if-not '(lambda (pr) (= (car pr) id)) (bht:tagged-pairs "TEXT" "BHT_KH" 1)))
            title (car (vl-remove-if 'bht:kh-extra-label-p labels)) stations (vl-remove-if-not 'bht:kh-station-label-p labels))
      (if (and title (= (length stations) 1))
        (progn
          (setq a (entget title) b (entget (car stations)) delta (mapcar '- (cdr (assoc 11 b)) (cdr (assoc 11 a))) rot (cdr (assoc 50 a)))
          (if (not (and (= (cdr (assoc 1 a)) (bht:cad-text (bht:kh-label id rec) (bht:kh-label-style (bht:kh-label id rec))))
                        (= (cdr (assoc 1 b)) (bht:cad-text (bht:get rec "ly_trinh_km") (bht:kh-label-style (bht:get rec "ly_trinh_km"))))
                        (equal (+ (* (car delta) (cos rot)) (* (cadr delta) (sin rot))) 0.0 1e-6)
                        (< (+ (* (- (car delta)) (sin rot)) (* (cadr delta) (cos rot))) 0.0)
                        (= (cdr (assoc 7 a)) (cdr (assoc 7 b))) (equal (cdr (assoc 40 a)) (cdr (assoc 40 b)) 1e-8)
                        (equal rot (cdr (assoc 50 b)) 1e-8))) (setq sl108-bad (1+ sl108-bad))))
        (setq sl108-bad (1+ sl108-bad))))))
(princ (strcat "\nSAMPLE-LABEL108 checked=" (itoa sl108-count) " bad=" (itoa sl108-bad) " ms=" (itoa sl108-ms)))
(princ (if (and (> sl108-count 0) (= sl108-bad 0)) "\nSAMPLE-LABEL108-LAYOUT-PASS" "\nSAMPLE-LABEL108-LAYOUT-FAIL"))
(princ)
