(setq field-fails 0 field-passes 0)
(defun fc (name ok) (if ok (setq field-passes (1+ field-passes)) (setq field-fails (1+ field-fails))) (princ (strcat "\n" (if ok "PASS FIELD " "FAIL FIELD ") name)))
(defun fm (id x y km h / e)
  (setq e (entmakex (list '(0 . "POINT") (cons 10 (list x y 0.0)))))
  (bht:pt-write-xdata e id "FIELD-QA" "1" id y x 0.0 "COC_TIEU" "QA" "" "")
  (bht:obj-write id (list (cons "object_id" id) '("nhom" . "COC_TIEU") (cons "marker_km" km) (cons "marker_h" h) (cons "pt" id))) e)
(fm "FA" 0.0 0.0 "39" "9") (fm "FB" 500.0 0.0 "40" "4") (fm "FC" 600.0 0.0 "40" "5")
(fm "FD" 700.0 0.0 "55" "6") (fm "FE" 800.0 0.0 "40" "7")
(fm "FX" 0.0 10.0 "39" "9") (fm "FY" 500.0 10.0 "40" "4")
(setq fi (bht:pt-all) fd (bht:field-chain-default))
(setq fr (bht:field-interval "FA" "FB" fd fi '(250.0 3.0 50.0)))
(fc "midpoint-no-route-required" (equal 40150.0 (cdr (assoc 'station fr)) 1e-8))
(fc "offset-XY-only" (equal 3.0 (cdr (assoc 'offset fr)) 1e-8))
(fc "fraction-half" (equal 0.5 (cdr (assoc 'fraction fr)) 1e-8))
(fc "bearing-east" (equal 0.0 (cdr (assoc 'bearing fr)) 1e-8))
(fc "before-start-no-extrapolation" (= "NGOAI_DOAN_COC" (cdr (assoc 'status (bht:field-interval "FA" "FB" fd fi '(-1.0 0.0 0.0))))))
(fc "after-end-no-extrapolation" (= "NGOAI_DOAN_COC" (cdr (assoc 'status (bht:field-interval "FA" "FB" fd fi '(501.0 0.0 0.0))))))
(fc "outside-offset" (= "XA_CHUOI_COC" (cdr (assoc 'status (bht:field-interval "FA" "FB" fd fi '(250.0 101.0 0.0))))))
(fc "reversed-station-rejected" (= "SAI_THU_TU_COC" (cdr (assoc 'status (bht:field-interval "FB" "FA" fd fi '(250.0 0.0 0.0))))))
(fc "bad-local-ratio-warning" (= "CAN_KIEM_TRA" (cdr (assoc 'status (bht:field-interval "FC" "FD" fd fi '(650.0 0.0 0.0))))))
(fc "duplicate-position-rejected" (= "COC_TRUNG_VI_TRI" (cdr (assoc 'status (bht:field-interval "FA" "FA" fd fi '(0.0 0.0 0.0))))))
(fc "missing-marker-rejected" (= "COC_KHONG_HOP_LE" (cdr (assoc 'status (bht:field-interval "FA" "MISSING" fd fi '(250.0 0.0 0.0))))))
(fc "save-chain" (= "OK" (car (bht:api-field-save "FIELD1" "QA" "FA FB FC FD FE" "20" "500" "0.03"))))
(fc "save-auto-activates-field-mode" (bht:field-mode-p))
(fc "duplicate-ID-chain-rejected" (= "LOI" (car (bht:api-field-save "DUP" "QA" "FA FA" "20" "500" "0.03"))))
(fm "FK" 900.0 0.0 "41" "0") (bht:obj-write "FK" (bht:set (bht:obj-read "FK") "nhom" "COT_KM"))
(fc "COT-KM-accepted" (= "OK" (car (bht:api-field-save "KM" "QA" "FA FK" "20" "500" "0.03"))))
(bht:api-field-mode "FIELD_MARKERS" "FIELD1")
(setq fr (bht:field-result nil '(250.0 1.0 0.0) fi))
(fc "bad-remote-segment-does-not-block" (equal 40150.0 (cdr (assoc 'station fr)) 1e-8))
(fc "bad-local-order-does-block" (= "SAI_THU_TU_COC" (cdr (assoc 'status (bht:field-result nil '(750.0 1.0 0.0) fi)))))
(bht:api-field-save "AMB" "QA" "FA FB FX FY" "20" "500" "0.03")
(fc "ambiguous-interval-never-nearest-guess" (= "NHIEU_DOAN_COC" (cdr (assoc 'status (bht:field-result nil '(250.0 5.0 0.0) fi)))))
(bht:api-field-mode "FIELD_MARKERS" "FIELD1")
(setq fe (entmakex '((0 . "POINT") (10 250.0 3.0 0.0))))
(bht:pt-write-xdata fe "SIGNPT" "FIELD-QA" "2" "SIGN" 3.0 250.0 0.0 "BIEN_BAO" "QA" "" "")
(bht:obj-write "SIGN" '(("object_id" . "SIGN") ("nhom" . "BIEN_BAO") ("ma_hieu" . "W.207a") ("so_tru" . "1") ("pt" . "SIGNPT") ("phia_duong" . "PHAI") ("ly_trinh_m" . "123") ("kh_free_x" . "99999")))
(setq original-point (entget fe '("BHT_PT")))
(fc "object-button-calculates-without-route" (= "OK" (car (bht:api-object-station "SIGN"))))
(setq frec (bht:obj-read "SIGN"))
(fc "value-persisted" (equal (atof (bht:get frec "ly_trinh_m")) 40150.0 1e-6))
(fc "source-and-anchors-persisted" (and (= "FIELD_MARKERS" (bht:get frec "station_source")) (= "FA" (bht:get frec "field_used_a")) (= "FB" (bht:get frec "field_used_b")) (= "FIELD1" (bht:get frec "field_chain_id"))))
(fc "not-road-offset" (and (= "" (bht:get frec "offset_m")) (= "" (bht:get frec "phia_tuyen")) (= "3.000" (bht:get frec "field_offset_m"))))
(fc "survey-side-preserved" (= "PHAI" (bht:get frec "phia_duong")))
(fc "RTK-not-moved" (equal original-point (entget fe '("BHT_PT"))))
(fc "free-symbol-location-unused" (= "99999" (bht:get frec "kh_free_x")))
(fc "explicit-pair-success" (= "OK" (car (bht:api-field-pair "SIGN" "FA" "FB"))))
(fc "explicit-pair-cancels-chain-binding" (= "" (bht:get (bht:obj-read "SIGN") "field_chain_id")))
(bht:api-field-mode "FIELD_MARKERS" "AMB")
(fc "explicit-pair-beats-ambiguous-active-chain" (= "OK" (car (bht:api-object-station "SIGN"))))
(setq before-failed (bht:obj-read "SIGN"))
(fc "wrong-pair-rejected" (= "LOI" (car (bht:api-field-pair "SIGN" "FB" "FC"))))
(fc "failed-pair-keeps-record" (equal before-failed (bht:obj-read "SIGN")))
(bht:api-field-mode "FIELD_MARKERS" "FIELD1") (bht:api-field-auto "SIGN")
(bht:obj-write "FB" (bht:set (bht:obj-read "FB") "marker_h" "3"))
(fc "edited-number-used-live" (equal 40100.0 (cdr (assoc 'station (bht:field-result (bht:obj-read "SIGN") '(250.0 3.0 0.0) (bht:pt-all)))) 1e-7))
(bht:obj-write "FB" (bht:set (bht:obj-read "FB") "marker_h" "4"))
(setq before-delete-station (bht:get (bht:obj-read "SIGN") "ly_trinh_m"))
(bht:api-field-delete "FIELD1")
(fc "deleted-bound-chain-no-fallback" (= "LOI" (car (bht:api-object-station "SIGN"))))
(fc "failure-preserves-old-station" (= before-delete-station (bht:get (bht:obj-read "SIGN") "ly_trinh_m")))
(bht:api-field-save "FIELD1" "QA" "FA FB FC FD FE" "20" "500" "0.03")
(bht:api-object-station "SIGN")
(setq fr (bht:field-interval "FA" "FB" '(("max_span" . "100")) (bht:pt-all) '(250.0 0.0 0.0)))
(fc "long-span-warning" (= "CAN_KIEM_TRA" (cdr (assoc 'status fr))))
(bht:api-field-pair "SIGN" "FA" "FB")
(setq rec (bht:set (bht:obj-read "SIGN") "sign_heading_mode" "FIELD_PERP"))
(fc "perpendicular-heading" (equal 0.0 (bht:kh-orientation-angle rec '(250.0 3.0 0.0)) 1e-6))
(bht:obj-write "SIGN" rec)
(bht:kh-free-apply "SIGN" '(250.0 5.0 0.0) 0.5 nil)
(defun field-transform (/ d) (setq d (entget (cdr (assoc "SIGN" (bht:tagged-pairs "INSERT" "BHT_KH" 1))))) (list (assoc 10 d) (assoc 41 d) (assoc 42 d) (assoc 43 d)))
(setq old-transform (field-transform))
(setq result (bht:kh-heading-apply '("SIGN") "FIELD_PERP" "" nil))
(fc "bulk-field-heading-one-sign" (= 1 (cdr (assoc 'rotated result))))
(fc "heading-preserves-location-scale" (equal old-transform (field-transform)))
(bht:field-objects)
(fc "batch-cannot-overwrite-marker-numbers" (= "39900.000" (bht:get (bht:obj-read "FA") "ly_trinh_m")))
(fc "API-mode-invalid-rejected" (= "LOI" (car (bht:api-field-mode "BAD" ""))))
(fc "legacy-route-mode-remains" (= "OK" (car (bht:api-field-mode "ROUTE" ""))))
(fc "legacy-route-no-tim-still-errors" (= "LOI" (car (bht:api-object-station "SIGN"))))
(bht:api-field-mode "FIELD_MARKERS" "FIELD1")
(fc "start-endpoint-exact" (equal 39900.0 (cdr (assoc 'station (bht:field-interval "FA" "FB" fd (bht:pt-all) '(0.0 0.0 0.0)))) 1e-8))
(fc "end-endpoint-exact" (equal 40400.0 (cdr (assoc 'station (bht:field-interval "FA" "FB" fd (bht:pt-all) '(500.0 0.0 0.0)))) 1e-8))
(bht:obj-write "SIGN" (bht:set (bht:set (bht:obj-read "SIGN") "field_pair_a" "") "field_pair_b" ""))
(bht:api-field-save "REVIEW" "QA" "FA FB" "20" "100" "0.03")
(setq saved-value (bht:get (bht:obj-read "SIGN") "ly_trinh_m"))
(fc "unconfirmed-warning-does-not-write" (= "LOI" (car (bht:api-field-auto "SIGN"))))
(fc "warning-keeps-old-value" (= saved-value (bht:get (bht:obj-read "SIGN") "ly_trinh_m")))
(bht:obj-write "FB" (bht:set (bht:obj-read "FB") "marker_h" "3"))
(fc "explicit-reviewed-pair-can-write-provisional" (= "OK" (car (bht:api-field-pair "SIGN" "FA" "FB"))))
(fc "provisional-not-marked-valid" (= "NEEDS_REVIEW" (bht:get (bht:obj-read "SIGN") "station_status")))
(bht:obj-write "FB" (bht:set (bht:obj-read "FB") "marker_h" "4"))
(setq old-fb (bht:obj-read "FB"))
(bht:obj-write "FB" (append old-fb '(("pt" . "MISSING-RTK"))))
(fc "partial-RTK-marker-rejected" (null (bht:field-marker "FB" (bht:pt-all))))
(bht:obj-write "FB" old-fb)
(bht:api-field-save "FIELD1" "QA" "FA FB FC FD FE" "20" "500" "0.03")
(bht:api-field-auto "SIGN")
(bht:api-field-save "FIELD1" "QA" "FA FB FC FD FE" "20" "500" "0.03")
(fc "chain-edit-marks-results-stale" (= "NEEDS_REVIEW" (bht:get (bht:obj-read "SIGN") "station_status")))
(bht:api-object-station "SIGN")
(fc "recalculate-clears-stale-warning" (= "" (bht:get (bht:obj-read "SIGN") "field_last_error")))
(bht:api-field-mode "FIELD_MARKERS" "AMB")
(fc "bound-object-keeps-its-chain" (= "OK" (car (bht:api-object-station "SIGN"))))
(bht:api-field-mode "FIELD_MARKERS" "FIELD1")
(bht:api-field-pair "SIGN" "FA" "FB")
(princ (strcat "\nFIELD-FINAL-PASS=" (itoa field-passes) " FIELD-FINAL-FAIL=" (itoa field-fails)))
(princ)
