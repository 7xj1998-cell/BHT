(setq v101-points (bht:pt-all) v101-objects (bht:rec-all "OBJ"))
(defun v101-places (/ out d)
 (foreach pair (bht:tagged-pairs "INSERT" "BHT_KH" 1)
  (setq d (entget (cdr pair)))
  (setq out (cons (mapcar '(lambda (key) (assoc key d)) '(5 10 41 42 43 50)) out))) out)
(setq v101-before (v101-places))
(setq v101-start (getvar "MILLISECS") v101-upgrade (bht:api-symbol-upgrade))
(setq v101-f (open (getenv "BHT101_UPGRADE_REPORT") "w" "utf8-bom"))
(defun v101-check (ok text) (write-line (strcat (if ok "PASS " "FAIL ") text) v101-f))
(v101-check (= (car v101-upgrade) "OK") (strcat "upgrade " (vl-prin1-to-string v101-upgrade)))
(write-line (strcat "upgrade_ms=" (itoa (- (getvar "MILLISECS") v101-start))) v101-f)
(v101-check (equal v101-before (v101-places)) "symbol handle position scale rotation unchanged")
(v101-check (equal v101-points (bht:pt-all)) "all survey point data unchanged")
(v101-check (equal v101-objects (bht:rec-all "OBJ")) "all object records unchanged")
(v101-check (= (bht:meta "symbol_build" "") "1.1.5") "symbol build updated")
(v101-check (= (car (bht:api-sign-fill "0")) "OK") "upgraded sample fill off")
(v101-check (= (car (bht:api-sign-fill "1")) "OK") "upgraded sample fill on")
(close v101-f)
(princ "\nV101-UPGRADE-COMPLETE")
