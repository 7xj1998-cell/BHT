(setq m114-count 0 m114-fails 0)
(defun m114-check (name ok)
  (setq m114-count (1+ m114-count))
  (if (not ok) (setq m114-fails (1+ m114-fails)))
  (princ (strcat "\n" (if ok "PASS MARKER114 " "FAIL MARKER114 ") name)))
(defun m114-insert (id) (cdr (assoc id (bht:tagged-pairs "INSERT" "BHT_KH" 1))))
(defun m114-leaders (id)
  (vl-remove-if-not '(lambda (p) (= (car p) id))
    (append (bht:tagged-pairs "LINE" "BHT_KH" 1) (bht:tagged-pairs "LWPOLYLINE" "BHT_KH" 1))))
(defun m114-snapshot ()
  (list (bht:rec-all "OBJ") (bht:rec-read "META" "CONFIG")
    (mapcar '(lambda (pr) (entget (cdr pr) '("*"))) (bht:tagged-pairs "*" "BHT_KH" 1))))
(defun m114-at (id pt)
  (equal pt (cdr (assoc 10 (entget (m114-insert id)))) 1e-7))
(defun m114-head (id / rot)
  (setq rot (cdr (assoc 50 (entget (m114-insert id)))))
  (list (- (cos rot)) (- (sin rot)) 0.0))
(defun m114-old-placement (id / e d rec)
  (setq e (m114-insert id) d (entget e) rec (bht:obj-read id))
  (entmod (append (bht:dxf-put (bht:dxf-put d 10 '(60.0 30.0 0.0)) 50 0.3)
             (list (bht:kh-xdata-ins id "TAY" '(60.0 30.0 0.0) 0.3 (cdr (assoc 41 d))))))
  (bht:obj-write id (append (bht:kh-free-clear rec)
    '(("kh_mode" . "TU_DO") ("kh_free_x" . "60") ("kh_free_y" . "30")
      ("kh_free_z" . "0") ("kh_free_rot" . "0.3") ("kh_via" . "25,20,0") ("kh_leader_mode" . "WAYPOINT"))))
  (entmakex (append '((0 . "LWPOLYLINE") (100 . "AcDbEntity") (8 . "BHT_KYHIEU")
    (100 . "AcDbPolyline") (90 . 3) (70 . 0) (10 20.0 5.0) (10 25.0 20.0) (10 60.0 30.0))
    (list (bht:kh-leader-xdata id)))))

(setq m114-road (entmakex '((0 . "LWPOLYLINE") (100 . "AcDbEntity")
  (100 . "AcDbPolyline") (90 . 2) (70 . 0) (10 0.0 0.0) (10 100.0 0.0))))
(bht:route-create "R114" m114-road "TIM_DUONG" 100.0 0.0 nil "QA")
(foreach row '(("ML" 20.0 5.0 "COC_TIEU") ("MR" 30.0 -5.0 "COC_TIEU")
              ("MN" 40.0 5.0 "COC_TIEU") ("MK" 60.0 5.0 "COC_TIEU")
              ("KM" 70.0 5.0 "COT_KM") ("BB" 80.0 5.0 "BIEN_BAO"))
  (setq e (entmakex (list '(0 . "POINT") (cons 10 (list (cadr row) (caddr row) 0.0)))))
  (bht:pt-write-xdata e (car row) "QA" "1" (car row) (caddr row) (cadr row) 0.0 (nth 3 row) "QA" "" "")
  (bht:obj-create (car row) (list (cons "nhom" (nth 3 row)) '("ma_hieu" . "W.209")
    '("so_tru" . "1") '("marker_km" . "46") '("marker_h" . "1") '("ly_trinh_m" . "46100")
    (cons "route_id" (if (= (car row) "MN") "" "R114"))) (list (car row)) T)
  (bht:obj-write (car row) (bht:set (bht:obj-read (car row)) "route_id" (if (= (car row) "MN") "" "R114"))))
(bht:symbol-sync nil)
(m114-check "marker-at-origin-no-leader" (and (m114-at "ML" '(20.0 5.0 0.0)) (null (m114-leaders "ML"))))
(m114-check "left-head-towards-center" (equal (m114-head "ML") '(0.0 -1.0 0.0) 1e-7))
(m114-check "right-head-towards-center" (equal (m114-head "MR") '(0.0 1.0 0.0) 1e-7))
(setq m114-points (bht:pt-all) m114-route (bht:rec-all "ROUTE")
      m114-km (entget (m114-insert "KM") '("*"))
      m114-stations (mapcar '(lambda (p) (cons (car p) (bht:get (cdr p) "ly_trinh_m"))) (bht:rec-all "OBJ")))
(m114-old-placement "ML") (m114-old-placement "MN") (m114-old-placement "MK")
(bht:layer "QA_MARKER_LOCK" 7)
(entmod (bht:dxf-put (entget (m114-insert "MK")) 8 "QA_MARKER_LOCK"))
(setq d (entget (tblobjname "LAYER" "QA_MARKER_LOCK")))
(entmod (bht:dxf-put d 70 (logior 4 (cdr (assoc 70 d)))))
(setq m114-locked (entget (m114-insert "MK") '("*")) m114-locked-rec (bht:obj-read "MK"))
(setq m114-result (bht:api-symbol-display "8" "GAP_KHUC"))
(m114-check "bulk-success" (= "OK" (car m114-result)))
(m114-check "bulk-repairs-old-manual-marker" (and (m114-at "ML" '(20.0 5.0 0.0)) (null (m114-leaders "ML"))
  (equal (m114-head "ML") '(0.0 -1.0 0.0) 1e-7) (= "" (bht:get (bht:obj-read "ML") "kh_mode"))))
(setq m114-label (entget (cdr (assoc "ML" (bht:tagged-pairs "TEXT" "BHT_KH" 1)))))
(m114-check "auto-label-returns-with-marker" (and (< (distance '(20.0 5.0 0.0) (cdr (assoc 11 m114-label))) 3.0)
  (equal (cdr (assoc 50 m114-label)) (/ pi 2.0) 1e-7)))
(m114-check "missing-route-anchors-and-keeps-angle" (and (m114-at "MN" '(40.0 5.0 0.0))
  (equal 0.3 (cdr (assoc 50 (entget (m114-insert "MN")))) 1e-7) (null (m114-leaders "MN"))))
(m114-check "missing-route-and-locked-reported" (and (vl-string-search "MN" (vl-princ-to-string m114-result))
  (vl-string-search "MK" (vl-princ-to-string m114-result))))
(m114-check "locked-marker-untouched" (and (equal m114-locked (entget (m114-insert "MK") '("*")))
  (equal m114-locked-rec (bht:obj-read "MK"))))
(m114-check "kilometre-post-untouched" (equal m114-km (entget (m114-insert "KM") '("*"))))
(m114-check "signs-still-offset-with-leaders" (and (not (m114-at "BB" '(80.0 5.0 0.0))) (m114-leaders "BB")))
(setq d (entget (tblobjname "LAYER" "QA_MARKER_LOCK"))) (entmod (bht:dxf-put d 70 0))
(setq m114-result (bht:api-symbol-center "R114" "10" "GAP_KHUC"))
(m114-check "chosen-center-orients-unlinked-marker" (and (= "OK" (car m114-result))
  (m114-at "MN" '(40.0 5.0 0.0)) (equal (m114-head "MN") '(0.0 -1.0 0.0) 1e-7)
  (= "" (bht:get (bht:obj-read "MN") "route_id"))))
(bht:symbol-sync '("ML" "MR" "MN" "MK"))
(m114-check "refresh-does-not-restore-marker-leaders" (vl-every '(lambda (id) (null (m114-leaders id))) '("ML" "MR" "MN" "MK")))
(m114-check "display-reference-persists-on-refresh" (equal (m114-head "MN") '(0.0 -1.0 0.0) 1e-7))
(setq m114-before (mapcar '(lambda (p) (entget (cdr p) '("*"))) (bht:tagged-pairs "*" "BHT_KH" 1)))
(bht:api-symbol-center "R114" "10" "GAP_KHUC")
(m114-check "repeated-layout-no-geometry-drift" (equal m114-before (mapcar '(lambda (p) (entget (cdr p) '("*"))) (bht:tagged-pairs "*" "BHT_KH" 1)) 1e-7))
(setq m114-before (m114-snapshot))
(m114-check "bad-input-no-change" (and (= "LOI" (car (bht:api-symbol-display "-1" "THANG"))) (equal m114-before (m114-snapshot))))
(setq m114-writer (eval 'bht:kh-marker-place-one) m114-calls 0)
(defun bht:kh-marker-place-one (oid index)
  (setq m114-calls (1+ m114-calls))
  (if (= m114-calls 2) (/ 1 0) (apply m114-writer (list oid index))))
(setq m114-result (bht:api-symbol-center "R114" "15" "THANG"))
(set 'bht:kh-marker-place-one m114-writer)
(m114-check "failure-rolls-back-signs-markers-records" (and (= "LOI" (car m114-result)) (equal m114-before (m114-snapshot))))
(m114-check "survey-route-and-station-preserved" (and (equal m114-points (bht:pt-all)) (equal m114-route (bht:rec-all "ROUTE"))
  (equal m114-stations (mapcar '(lambda (p) (cons (car p) (bht:get (cdr p) "ly_trinh_m"))) (bht:rec-all "OBJ")))))

(setq m114-arc (entmakex '((0 . "LWPOLYLINE") (100 . "AcDbEntity") (100 . "AcDbPolyline")
  (90 . 2) (70 . 0) (10 0.0 0.0) (42 . 1.0) (10 100.0 0.0))))
(bht:route-create "ARC114" m114-arc "TIM_DUONG" 100.0 0.0 nil "QA")
(setq m114-arcpoint (list (- 50.0 (/ 55.0 (sqrt 2.0))) (- (/ 55.0 (sqrt 2.0))) 0.0)
      e (entmakex (list '(0 . "POINT") (cons 10 m114-arcpoint))))
(bht:pt-write-xdata e "MC" "QA" "1" "MC" (cadr m114-arcpoint) (car m114-arcpoint) 0.0 "COC_TIEU" "QA" "" "")
(bht:obj-create "MC" '(("nhom" . "COC_TIEU") ("route_id" . "ARC114")) '("MC") T)
(bht:obj-write "MC" (bht:set (bht:obj-read "MC") "route_id" "ARC114"))
(bht:symbol-sync '("MC"))
(m114-check "curved-route-local-normal" (and (m114-at "MC" m114-arcpoint)
  (equal (m114-head "MC") (list (/ 1.0 (sqrt 2.0)) (/ 1.0 (sqrt 2.0)) 0.0) 1e-7) (null (m114-leaders "MC"))))
(bht:route-write "ARC114" (bht:set (bht:route-read "ARC114") "direction" "-1"))
(bht:symbol-sync '("MC"))
(m114-check "reversed-route-keeps-head-toward-road" (equal (m114-head "MC") (list (/ 1.0 (sqrt 2.0)) (/ 1.0 (sqrt 2.0)) 0.0) 1e-7))
(m114-check "single-marker-placement" (= "OK" (car (bht:api-sign-place "MC" "DIRECT" "ROUTE" "0"))))
(princ (strcat "\nMARKER114-CHECKS=" (itoa m114-count) " FAIL=" (itoa m114-fails))) (princ)
