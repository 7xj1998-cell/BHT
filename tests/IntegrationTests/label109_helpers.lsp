(setq l109-n 0 l109-fail 0)
(defun l109-check (name ok)
 (setq l109-n (1+ l109-n)) (if (not ok) (setq l109-fail (1+ l109-fail)))
 (princ (strcat "\n" (if ok "PASS LABEL109 " "FAIL LABEL109 ") name)))
(defun l109-cluster-p (angle / groups group origin e d offset y previous ok kind labels index)
 (setq ok T offset (cdr (assoc 'off (bht:lbl-settings))) index (bht:pt-all))
 (foreach group (bht:group-pairs (bht:tagged-pairs "TEXT" "BHT_NHAN" 1))
  (setq origin (bht:pv (bht:pt-find (car group) index) 'xyz) y offset previous nil labels nil)
  (foreach kind '("TEN" "MOTA" "CAODO" "ID")
   (setq labels (append labels (vl-remove-if-not '(lambda (e) (= kind (cadr (bht:xget e "BHT_NHAN")))) (cdr group)))))
  (foreach e labels
   (setq d (entget e)) (if previous (setq y (- y (* 1.5 (max previous (cdr (assoc 40 d)))))))
   (if (not (and (equal (cdr (assoc 10 d)) (bht:label-local origin offset y angle) 1e-7)
                 (equal (cdr (assoc 50 d)) angle 1e-8))) (setq ok nil))
   (setq previous (cdr (assoc 40 d))))) ok)
