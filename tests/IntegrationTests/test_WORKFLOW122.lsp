(setq w122-n 0 w122-fail 0)
(defun w122-check (name ok) (setq w122-n (1+ w122-n)) (if (not ok) (setq w122-fail (1+ w122-fail))) (princ (strcat "\n" (if ok "PASS WORKFLOW122 " "FAIL WORKFLOW122 ") name)))
(setq w122-line (entmakex '((0 . "LWPOLYLINE") (100 . "AcDbEntity") (100 . "AcDbPolyline") (90 . 2) (70 . 0) (10 0.0 0.0) (10 1000.0 0.0))))
(bht:route-create "DEST122" w122-line "TIM_RANH" 100.0 0.0 nil "TDTSolution 9.1")
(setq w122-rec (bht:route-read "DEST122"))
(w122-check "missing-raw-distance-rejected-before-arithmetic" (null (bht:route-distance-from-raw w122-rec w122-line nil)))
(w122-check "outside-raw-distance-not-wrapped-on-open-route" (null (bht:route-distance-from-raw w122-rec w122-line 1001.0)))
(setq w122-p (entmakex '((0 . "POINT") (10 100.0 2.0 0.0))))
(bht:pt-write-xdata w122-p "P122" "QA" "1" "1" 2.0 100.0 0.0 "COC_TIEU" "QA" "" "")
(bht:obj-create "MARK122" '(("nhom" . "COC_TIEU") ("marker_km" . "42") ("marker_h" . "1")) '("P122") T)
(w122-check "fresh-tdt-route-never-borrows-imported-marker" (null (car (bht:route-object-controls w122-rec))))
(w122-check "fresh-tdt-route-cannot-recalculate-from-old-caption" (eq (car (bht:route-recalculate-plan "DEST122")) 'LOI))
(setq w122-rec (bht:set (bht:set w122-rec "nguon" "Polyline") "tdt_source_handle" "ABC"))
(w122-check "tdt-source-handle-also-isolates-controls" (null (car (bht:route-object-controls w122-rec))))
(setq w122-rec (bht:set (bht:set w122-rec "tdt_source_handle" "") "station_control_mode" "ROUTE_ONLY"))
(w122-check "route-only-policy-is-explicit" (null (car (bht:route-object-controls w122-rec))))
;; Fault at the bridge boundary: reject the whole scan, never turn nil into zero.
(setq w122-bridge BHTTDT91STAKES)
(defun BHTTDT91STAKES (handle offset) '("OK" "50140||0|10|0|TDT_COC|STAKE122|Km50+140|TDT|95"))
(setq w122-bad (vl-catch-all-apply 'bht:tdt-stake-candidates (list w122-rec)))
(w122-check "malformed-bridge-row-returns-explained-error-not-numberp-nil" (and (not (vl-catch-all-error-p w122-bad)) (eq (car w122-bad) 'LOI)))
(defun BHTTDT91STAKES (handle offset) '("OK" "50140|0|0|0|0|TDT_COC|A122|Km50+140|TDT|95" "bad row"))
(w122-check "mixed-valid-invalid-scan-does-not-offer-partial-controls" (eq (car (bht:tdt-stake-candidates w122-rec)) 'LOI))
(defun BHTTDT91STAKES (handle offset) '("OK" "50140|0|0|0|0|TDT_COC|A122|Km50+140|TDT|95" "51140|1000|0|1000|0|TDT_COC|B122|Km51+140|TDT|95"))
(setq w122-good (bht:tdt-stake-candidates w122-rec))
(w122-check "valid-zero-start-and-end-stakes-retained" (= 2 (length w122-good)))
(setq BHTTDT91STAKES w122-bridge)
(bht:route-add-tdt-stakes "DEST122" w122-good (bht:tdt-stake-issues w122-good))
(w122-check "confirmed-tdt-controls-replace-fallback-policy" (= 2 (length (car (bht:route-object-controls (bht:route-read "DEST122"))))))
(w122-check "survey-marker-observation-preserved" (= "42100.000" (bht:get (bht:obj-read "MARK122") "ly_trinh_m")))
(princ (strcat "\nWORKFLOW122-CHECKS=" (itoa w122-n) " FAIL=" (itoa w122-fail)))
(princ)
