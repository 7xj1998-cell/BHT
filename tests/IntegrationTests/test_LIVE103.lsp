(vl-load-com)
(if (/= (getvar "DWGNAME") "BOT830-saved-copy.dwg") (progn (princ "Wrong QA drawing") (exit)))
(setq qa-path "D:/lisp/BHT/sharing-0654/source/build/v1.0.3/qa/live-cad.txt")
(setq qa-f (open qa-path "w" "utf8-bom"))
(write-line (strcat "Runtime=" *bht-version*) qa-f)
(write-line (strcat "Drawing=" (getvar "DWGPREFIX") (getvar "DWGNAME")) qa-f)
(write-line (strcat "Method=" (bht:meta "station_method" "ROUTE")) qa-f)
(write-line (strcat "Objects=" (itoa (length (bht:obj-ids))) ";Points=" (itoa (length (bht:pt-all)))) qa-f)
(setq qa-records (bht:rec-all "OBJ") qa-points (bht:pt-all) qa-method (bht:meta "station_method" "ROUTE"))
(foreach line (bht:api-check) (write-line line qa-f))
(command "_.UNDO" "_Begin")
(setq qa-time (getvar "MILLISECS"))
(c:BHTLYTRINH)
(write-line (strcat "StationMillis=" (itoa (- (getvar "MILLISECS") qa-time))) qa-f)
(write-line (strcat "MethodPreserved=" (if (= qa-method (bht:meta "station_method" "ROUTE")) "PASS" "FAIL")) qa-f)
(write-line (strcat "PointsPreserved=" (if (equal qa-points (bht:pt-all)) "PASS" "FAIL")) qa-f)
(command "_.UNDO" "_End")
(command "_.U")
(write-line (strcat "UndoRecords=" (if (equal qa-records (bht:rec-all "OBJ")) "PASS" "FAIL")) qa-f)
(close qa-f)
(princ "\nBHT LIVE QA completed on copy")
(princ)
