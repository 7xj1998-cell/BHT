(signs-check "upgrade-preserves-manual-and-auto-transform" (equal upgrade-transform-before (list (upgrade-transform upgrade-manual) (upgrade-transform upgrade-auto)) 1e-9))
(signs-check "upgrade-preserves-placement-mode-xdata" (equal upgrade-xdata-before (list (assoc -3 (entget upgrade-manual '("BHT_KH"))) (assoc -3 (entget upgrade-auto '("BHT_KH"))))))
(signs-check "upgrade-replaces-old-geometry-preserves-fill-off" (and (upgrade-outline-p "OBJ-UP-BIEN_BAO") (upgrade-outline-p "OBJ-UP-AUTO") (wcmatch (cdr (assoc 2 (entget upgrade-manual))) "BHT_*_V0633_*")))
(signs-check "upgrade-keeps-all-records-and-RTK" (and (equal upgrade-records-before (mapcar '(lambda (id) (cons id (bht:obj-read id))) (bht:obj-ids))) (equal upgrade-RTK-before (entget survey '("BHT_PT")))))
(signs-check "upgrade-does-not-create-unplaced-symbol" (null (assoc "OBJ-UP-NOSYMBOL" (bht:tagged-pairs "INSERT" "BHT_KH" 1))))
(signs-check "upgrade-marker-current" (= (bht:meta "symbol_build" "") *bht-version*))
(setq upgrade-after (entget upgrade-manual '("BHT_KH")))
(signs-check "upgrade-repeat-no-change" (and (= (car (bht:api-symbol-upgrade)) "OK") (equal upgrade-after (entget upgrade-manual '("BHT_KH")))))
(bht:photo-write "UP-PHOTO" '(("photo_id" . "UP-PHOTO") ("doi_tuong" . "OBJ-UP-BIEN_BAO") ("doi_tuong" . "OBJ-UP-AUTO") ("file_name" . "original.jpg")))
(bht:obj-write "OBJ-UP-BIEN_BAO" (bht:set-all (bht:obj-read "OBJ-UP-BIEN_BAO") "anh" '("UP-PHOTO|before")))
(setq upgrade-other-before (bht:obj-read "OBJ-UP-AUTO") upgrade-point-before (entget survey '("BHT_PT")))
(signs-check "delete-api-success" (= (car (bht:api-object-delete "obj-up-bien_bao")) "OK"))
(signs-check "delete-removes-record-symbol-label-leader" (and (null (bht:obj-read "OBJ-UP-BIEN_BAO")) (null (assoc "OBJ-UP-BIEN_BAO" (bht:tagged-pairs "INSERT" "BHT_KH" 1))) (null (assoc "OBJ-UP-BIEN_BAO" (bht:tagged-pairs "TEXT" "BHT_KH" 1))) (null (assoc "OBJ-UP-BIEN_BAO" (bht:tagged-pairs "LINE" "BHT_KH" 1)))))
(signs-check "delete-keeps-RTK-and-other-record" (and (equal upgrade-point-before (entget survey '("BHT_PT"))) (equal upgrade-other-before (bht:obj-read "OBJ-UP-AUTO"))))
(signs-check "delete-keeps-photo-unlinks-only-deleted-object" (and (bht:photo-read "UP-PHOTO") (equal (bht:get-all (bht:photo-read "UP-PHOTO") "doi_tuong") '("OBJ-UP-AUTO")) (= (bht:get (bht:photo-read "UP-PHOTO") "file_name") "original.jpg")))
(setq upgrade-ids-before (bht:obj-ids))
(signs-check "delete-missing-id-error-no-change" (and (= (car (bht:api-object-delete "OBJ-UP-BIEN_BAO")) "LOI") (= (car (bht:api-object-delete "")) "LOI") (equal upgrade-ids-before (bht:obj-ids))))
(foreach id (append upgrade-pairs '("OBJ-UP-AUTO" "OBJ-UP-NOSYMBOL")) (bht:obj-delete id))
(bht:api-sign-fill "1")
(princ (strcat "\nSIGN-TEST-FAIL=" (itoa *sign-test-fail*)))
(princ "\nUPGRADE-TEST-COMPLETED")
