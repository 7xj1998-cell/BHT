(vl-load-com)
(setq r106-n 0 r106-fail 0)
(defun r106-check (name ok)
  (setq r106-n (1+ r106-n)) (if (not ok) (setq r106-fail (1+ r106-fail)))
  (princ (strcat "\n" (if ok "PASS ROAD106 " "FAIL ROAD106 ") name)))
(defun r106-bounds (oid / e labels)
  (setq e (cdr (assoc oid (bht:tagged-pairs "INSERT" "BHT_KH" 1)))
        labels (mapcar 'cdr (vl-remove-if-not '(lambda (p) (= (car p) oid)) (bht:tagged-pairs "TEXT" "BHT_KH" 1))))
  (BHTDISPLAYBOUNDS (cons e labels)))
(defun r106-snapshot ()
  (list (bht:rec-all "OBJ") (bht:rec-read "META" "CONFIG")
    (mapcar '(lambda (pr) (entget (cdr pr) '("*"))) (append (bht:tagged-pairs "*" "BHT_KH" 1) (bht:tagged-pairs "INSERT" "BHT_SIGN_ORIGIN" 1)))))
(defun r106-angles ()
  (mapcar '(lambda (pr / d) (setq d (entget (cdr pr))) (list (car pr) (assoc 41 d) (assoc 42 d) (assoc 43 d))) (bht:tagged-pairs "INSERT" "BHT_KH" 1)))
(defun r106-apply (ent left right gap dir mode)
  (bht:api-run 'bht:kh-road-apply (list ent left right gap dir mode)))
(foreach row '(("A" 20.0 2.0) ("B" 50.0 -3.0) ("C" 0.0 0.0) ("D" -20.0 5.0) ("A2" 23.0 2.0))
  (setq e (entmakex (list '(0 . "POINT") (cons 10 (list (cadr row) (caddr row) 0.0)))))
  (bht:pt-write-xdata e (car row) "QA" "1" (car row) (caddr row) (cadr row) 0.0 "BIEN_BAO" "QA" "" ""))
(foreach row '(("LEFT" "A") ("RIGHT" "B") ("CENTER" "C") ("BEYOND" "D"))
  (bht:obj-create (car row) '(("nhom" . "BIEN_BAO") ("ma_hieu" . "W.209") ("so_tru" . "1") ("ly_trinh_m" . "40123.456")) (list (cadr row)) T))
(bht:obj-create "TWO" '(("nhom" . "BIEN_BAO") ("ma_hieu" . "W.209") ("so_tru" . "2")) '("A" "A2") T)
(bht:obj-create "LIGHT" '(("nhom" . "DEN_TH")) '("B") T)
(bht:kh-free-apply "LEFT" '(20.0 5.0 0.0) 0.4 nil)
(bht:kh-free-apply "RIGHT" '(50.0 -5.0 0.0) 2.2 nil)
(setq e (cdr (assoc "RIGHT" (bht:tagged-pairs "INSERT" "BHT_KH" 1))) d (entget e))
(entmod (bht:dxf-put (bht:dxf-put d 41 2.0) 42 2.0))
(bht:kh-free-apply "TWO" '(23.0 5.0 0.0) 0.8 nil)
(bht:kh-free-apply "CENTER" '(0.0 3.0 0.0) 0.0 nil)
(bht:kh-free-apply "BEYOND" '(-20.0 8.0 0.0) 0.0 nil)
(bht:kh-free-apply "LIGHT" '(50.0 -6.0 0.0) 0.2 nil)
(bht:obj-write "LEFT" (bht:set (bht:obj-read "LEFT") "ly_trinh_m" "40123.456"))
(setq r106-road (entmakex '((0 . "LWPOLYLINE") (100 . "AcDbEntity") (100 . "AcDbPolyline") (90 . 2) (70 . 0) (10 0.0 0.0) (10 100.0 0.0))))
(setq r106-points (bht:pt-all) r106-angle (r106-angles) r106-routes (bht:rec-all "ROUTE") r106-chain (bht:rec-all "FIELD_CHAIN") r106-before (r106-snapshot))
(r106-check "native-bounds-includes-labels" (and (listp (r106-bounds "LEFT")) (= 4 (length (r106-bounds "LEFT")))))
(r106-check "reject-negative-width-without-changes" (and (= "LOI" (car (r106-apply r106-road "-1" "5" "1" 1 "THANG"))) (equal r106-before (r106-snapshot))))
(r106-check "reject-invalid-mode-without-changes" (and (= "LOI" (car (r106-apply r106-road "5" "5" "1" 1 "BAD"))) (equal r106-before (r106-snapshot))))
(setq closed (entmakex '((0 . "LWPOLYLINE") (100 . "AcDbEntity") (100 . "AcDbPolyline") (90 . 3) (70 . 1) (10 0.0 0.0) (10 100.0 0.0) (10 100.0 30.0))))
(r106-check "reject-closed-PL" (and (= "LOI" (car (r106-apply closed "5" "5" "1" 1 "THANG"))) (equal r106-before (r106-snapshot))))
(setq result (r106-apply r106-road "8" "5" "1" 1 "THANG")) (princ result)
(r106-check "apply-both-sides-success" (= "OK" (car result)))
(r106-check "left-clearance-includes-rotated-geometry-and-label" (equal (nth 1 (r106-bounds "LEFT")) 9.0 1e-6))
(r106-check "right-clearance-includes-large-rotated-block" (equal (nth 3 (r106-bounds "RIGHT")) -6.0 1e-6))
(r106-check "two-post-sign-clears-road" (equal (nth 1 (r106-bounds "TWO")) 9.0 1e-6))
(r106-check "light-clears-road" (equal (nth 3 (r106-bounds "LIGHT")) -6.0 1e-6))
(r106-check "center-and-beyond-not-moved" (vl-every '(lambda (id) (equal (cdr (assoc id (car r106-before))) (bht:obj-read id))) '("CENTER" "BEYOND")))
(r106-check "straight-leaders" (not (vl-some '(lambda (p) (member (car p) '("LEFT" "RIGHT" "TWO" "LIGHT"))) (bht:tagged-pairs "LWPOLYLINE" "BHT_KH" 1))))
(r106-check "survey-and-scales-preserved" (and (equal r106-points (bht:pt-all)) (equal r106-angle (r106-angles))))
(r106-check "reference-not-used-for-chainage" (and (equal r106-routes (bht:rec-all "ROUTE")) (equal r106-chain (bht:rec-all "FIELD_CHAIN")) (= "40123.456" (bht:get (bht:obj-read "LEFT") "ly_trinh_m"))))
(setq r106-after (r106-snapshot))
(r106-apply r106-road "8" "5" "1" 1 "THANG")
(r106-check "repeat-does-not-drift" (equal (nth 2 r106-after) (nth 2 (r106-snapshot)) 1e-6))
(r106-apply r106-road "8" "5" "1" -1 "GAP_KHUC")
(r106-check "reverse-reference-swaps-widths-not-geometric-side" (and (equal (nth 1 (r106-bounds "LEFT")) 6.0 1e-6) (equal (nth 3 (r106-bounds "RIGHT")) -9.0 1e-6)))
(r106-check "bent-leaders-and-points-kept" (and (bht:tagged-pairs "LWPOLYLINE" "BHT_KH" 1) (equal r106-points (bht:pt-all))))
(setq r106-before (r106-snapshot) writer (eval 'bht:kh-leader-sync-source))
(defun bht:kh-leader-sync-source (oid a b ents via source) (/ 1 0))
(setq result (r106-apply r106-road "15" "7" "2" 1 "THANG"))
(set 'bht:kh-leader-sync-source writer)
(r106-check "failure-rolls-back-full-display-records-and-meta" (and (= "LOI" (car result)) (equal r106-before (r106-snapshot))))
(setq picker (eval 'bht:kh-road-pick))
(defun bht:kh-road-pick () '(HUY))
(r106-check "cancel-keeps-drawing" (and (= "OK" (car (bht:api-symbol-road "1" "8" "5" "THANG"))) (equal r106-before (r106-snapshot))))
(set 'bht:kh-road-pick picker)
(setq r106-before (r106-snapshot) boundsfn (eval 'BHTDISPLAYBOUNDS))
(defun BHTDISPLAYBOUNDS (entities) nil)
(r106-check "unknown-extents-skips-without-changes" (and (= "OK" (car (r106-apply r106-road "8" "5" "1" 1 "THANG"))) (equal r106-before (r106-snapshot))))
(set 'BHTDISPLAYBOUNDS boundsfn)
(setq layer (tblobjname "LAYER" "BHT_KYHIEU") ld (entget layer))
(entmod (bht:dxf-put ld 70 (logior 4 (cdr (assoc 70 ld)))))
(setq r106-before (r106-snapshot))
(r106-check "locked-components-not-moved-or-rewritten" (and (= "OK" (car (r106-apply r106-road "8" "5" "2" 1 "THANG"))) (equal r106-before (r106-snapshot))))
(entmod ld)
(setq curve (entmakex '((0 . "LWPOLYLINE") (100 . "AcDbEntity") (100 . "AcDbPolyline") (90 . 2) (70 . 0) (10 0.0 0.0) (42 . 0.15) (10 100.0 0.0))))
(r106-check "curved-reference-success" (= "OK" (car (r106-apply curve "5" "5" "1" 1 "GAP_KHUC"))))
(foreach id '("LEFT" "RIGHT" "TWO" "LIGHT")
  (setq b (r106-bounds id) center (list (/ (+ (car b) (nth 2 b)) 2.0) (/ (+ (cadr b) (nth 3 b)) 2.0) 0.0)
        radius (/ (distance (list (car b) (cadr b)) (list (nth 2 b) (nth 3 b))) 2.0))
  (r106-check (strcat "curved-PL-full-geometry-clear-" id) (>= (- (cadr (bht:curve-project curve center)) radius) (- 6.0 1e-6))))
(r106-check "curved-layout-keeps-survey-and-scales" (and (equal r106-points (bht:pt-all)) (equal r106-angle (r106-angles))))
;; Leave a straight-road example for save/reopen and visual review.
(bht:route-create "TIM106" r106-road "TIM_DUONG" 100.0 0.0 nil "QA")
(setq r106-center-record (bht:route-read "TIM106") r106-road-width (bht:meta "symbol_road_left" ""))
(r106-check "loaded-center-api-success" (= "OK" (car (bht:api-symbol-center "TIM106" "6" "THANG"))))
(r106-check "center-distance-measured-to-full-display" (and (equal (nth 1 (r106-bounds "LEFT")) 6.0 1e-6) (equal (nth 3 (r106-bounds "RIGHT")) -6.0 1e-6)))
(r106-check "center-mode-stored-and-road-widths-preserved" (and (= "CENTER" (bht:meta "symbol_layout_method" "")) (= "TIM106" (bht:meta "symbol_center_route" "")) (equal 6.0 (bht:num (bht:meta "symbol_center_distance" "")) 1e-8) (= r106-road-width (bht:meta "symbol_road_left" ""))))
(r106-check "center-reference-and-chainage-kept" (and (equal r106-center-record (bht:route-read "TIM106")) (equal r106-points (bht:pt-all)) (= "40123.456" (bht:get (bht:obj-read "LEFT") "ly_trinh_m"))))
(setq r106-before (r106-snapshot))
(r106-check "missing-center-refuses-without-changing-display" (and (= "LOI" (car (bht:api-symbol-center "MISSING" "6" "THANG"))) (equal r106-before (r106-snapshot))))
;; A route can be explicitly selected for display without changing its type or marks.
(foreach typ '("KHAC" "TIM_RANH" "" "tim_duong")
  (setq cid (strcat "REF107-" (itoa (1+ r106-n))))
  (bht:route-create cid r106-road typ 100.0 20.0 nil "QA107")
  (bht:route-write cid (append (bht:route-read cid) '(("moc" . "10|40000|40000|rtk|QA"))))
  (setq route107-before (bht:rec-all "ROUTE") points107-before (bht:pt-all) chains107-before (bht:rec-all "FIELD_CHAIN"))
  (r106-check (strcat "explicit-center-accepts-route-type-" typ) (= "OK" (car (bht:api-symbol-center cid "7" "THANG"))))
  (r106-check (strcat "explicit-center-keeps-type-marks-and-chainage-" typ)
    (and (equal route107-before (bht:rec-all "ROUTE")) (equal points107-before (bht:pt-all))
         (equal chains107-before (bht:rec-all "FIELD_CHAIN")) (= "40123.456" (bht:get (bht:obj-read "LEFT") "ly_trinh_m"))
         (= "CENTER" (bht:meta "symbol_layout_method" "")) (= cid (bht:meta "symbol_center_route" "")))))
(bht:route-create "CLOSED107" closed "KHAC" 100.0 0.0 nil "QA107")
(setq r106-before (r106-snapshot))
(r106-check "closed-loaded-route-rejected-without-changes" (and (= "LOI" (car (bht:api-symbol-center "CLOSED107" "6" "THANG"))) (equal r106-before (r106-snapshot))))
(setq gone107 (entmakex '((0 . "LWPOLYLINE") (100 . "AcDbEntity") (100 . "AcDbPolyline") (90 . 2) (70 . 0) (10 0.0 0.0) (10 100.0 0.0))))
(bht:route-create "GONE107" gone107 "KHAC" 100.0 0.0 nil "QA107") (entdel gone107)
(setq r106-before (r106-snapshot))
(r106-check "deleted-loaded-route-rejected-without-changes" (and (= "LOI" (car (bht:api-symbol-center "GONE107" "6" "THANG"))) (equal r106-before (r106-snapshot))))
(setq broken (entmakex '((0 . "LWPOLYLINE") (100 . "AcDbEntity") (100 . "AcDbPolyline") (90 . 3) (70 . 0) (10 0.0 0.0) (10 65.0 0.0) (10 100.0 20.0))))
(bht:route-create "GAY106" broken "TIM_DUONG" 100.0 0.0 nil "QA")
(r106-check "broken-center-uses-local-direction" (= "OK" (car (bht:api-symbol-center "GAY106" "6" "GAP_KHUC"))))
(setq cp106 (bht:kh-road-frame broken '(90.0 30.0 0.0) 1))
(r106-check "broken-center-normal-varies-by-segment" (and cp106 (< (car (nth 1 cp106)) -0.1) (> (cadr (nth 1 cp106)) 0.5)))
(entmake '((0 . "POLYLINE") (66 . 1) (70 . 0) (10 0.0 0.0 0.0)))
(setq oldpoly (entlast))
(entmake '((0 . "VERTEX") (10 0.0 0.0 0.0)))
(entmake '((0 . "VERTEX") (10 100.0 0.0 0.0)))
(entmake '((0 . "SEQEND")))
(r106-check "classic-2D-polyline-accepted" (and (bht:kh-road-valid-p oldpoly) (= "OK" (car (r106-apply oldpoly "8" "5" "1" 1 "GAP_KHUC")))))
(r106-apply r106-road "8" "5" "1" 1 "GAP_KHUC")
(princ (strcat "\nROAD106-CHECKS=" (itoa r106-n) " FAIL=" (itoa r106-fail))) (princ)
