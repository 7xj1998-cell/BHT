(setq v1-pass 0 v1-fail 0)
(defun v1-assert (name ok)
 (if ok (setq v1-pass (1+ v1-pass)) (setq v1-fail (1+ v1-fail)))
 (princ (strcat "\n" (if ok "PASS INDEX " "FAIL INDEX ") name)))
(defun v1-index-check (/ index other *bht-fast-point-source* *bht-fast-point-tree* i id)
 (setq i 0)
 (repeat 1000 (setq id (strcat "P" (itoa i)) index (cons (cons id (list (cons 'id id) (cons 'xyz (list i 0 0)))) index) i (1+ i)))
 (setq *bht-fast-point-source* index *bht-fast-point-tree* (bht:pt-lookup-tree index))
 (v1-assert "tree-built" *bht-fast-point-tree*)
 (foreach item index (v1-assert "same-as-legacy-lookup" (equal (bht:pt-find (strcase (car item) T) index) (cdr item))))
 (v1-assert "missing-point" (null (bht:pt-find "MISSING" index)))
 (setq other (list (cons "P1" '((id . "NEW")))))
 (v1-assert "different-index-not-cached" (equal (bht:pt-find "P1" other) '((id . "NEW"))))
 (setq index (append other other) *bht-fast-point-source* index *bht-fast-point-tree* (bht:pt-lookup-tree index))
 (v1-assert "duplicate-falls-back" (null *bht-fast-point-tree*))
 (v1-assert "duplicate-keeps-first" (equal (bht:pt-find "P1" index) (cdar index))))
(v1-index-check)
(v1-assert "no-cache-outside-batch" (and (null *bht-fast-point-tree*) (null *bht-fast-point-source*)))
(princ (strcat "\nINDEX-PASS=" (itoa v1-pass) " INDEX-FAIL=" (itoa v1-fail)))
