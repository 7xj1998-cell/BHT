(vl-load-com)
(setq qa-dir (getenv "BHT103_SAMPLE") qa-phase (getenv "BHT103_PHASE"))
(defun qa103-points ()
 (mapcar '(lambda (p) (list (car p) (bht:pv (cdr p) 'xyz) (bht:pv (cdr p) 'src) (bht:pv (cdr p) 'n) (bht:pv (cdr p) 'e))) (bht:pt-all)))
(defun qa103-symbols (/ out d)
 (foreach p (bht:tagged-pairs "INSERT" "BHT_KH" 1)
  (setq d (entget (cdr p)))
  (setq out (cons (list (car p) (assoc 5 d) (assoc 2 d) (assoc 10 d) (assoc 41 d) (assoc 42 d) (assoc 43 d) (assoc 50 d)) out))) out)
(defun qa103-stable (v)
 (cond ((= (type v) 'REAL) (rtos v 2 12))
       ((= (type v) 'LIST) (cons (qa103-stable (car v)) (qa103-stable (cdr v))))
       (T v)))
(defun qa103-snapshot () (qa103-stable (list (qa103-points) (qa103-symbols) (bht:rec-all "OBJ") (bht:meta "station_method" "ROUTE") (bht:rec-all "FIELD_CHAIN"))))
(defun qa103-check (name ok) (write-line (strcat (if ok "PASS " "FAIL ") name) qa-log))
(setq qa-log (open (strcat qa-dir "/" qa-phase ".txt") "w" "utf8-bom"))
(write-line (strcat "Runtime=" *bht-version*) qa-log)
(if (= qa-phase "create")
 (progn
  (setq qa-points (qa103-points) qa-symbols (qa103-symbols) qa-method (bht:meta "station_method" "ROUTE") qa-chain (bht:rec-all "FIELD_CHAIN"))
  (setq qa-f (open (strcat qa-dir "/diagnostics-before.txt") "w" "utf8-bom"))
  (foreach line (bht:api-check) (write-line line qa-f)) (close qa-f)
  (setq qa-times nil)
  (repeat 5
   (setq qa-start (getvar "MILLISECS") qa-result (bht:station-objects))
   (setq qa-times (append qa-times (list (- (getvar "MILLISECS") qa-start)))))
  (write-line (strcat "Method=" qa-method) qa-log)
  (write-line (strcat "Milliseconds=" (vl-prin1-to-string qa-times)) qa-log)
  (write-line (strcat "Result=" (vl-prin1-to-string qa-result)) qa-log)
  (qa103-check "point coordinates and source preserved" (equal qa-points (qa103-points)))
  (qa103-check "symbol handles geometry rotation scale preserved" (equal qa-symbols (qa103-symbols)))
  (qa103-check "station method preserved" (= qa-method (bht:meta "station_method" "ROUTE")))
  (qa103-check "marker groups and approvals preserved" (equal qa-chain (bht:rec-all "FIELD_CHAIN")))
  (qa103-check "every object accounted for" (= (apply '+ qa-result) (length (bht:obj-ids))))
  (setq qa-f (open (strcat qa-dir "/objects-after.tsv") "w" "utf8-bom"))
  (write-line "ID\tGROUP\tSTATION\tSTATUS\tNOTE" qa-f)
  (foreach p (bht:rec-all "OBJ")
   (write-line (strcat (car p) "\t" (bht:get (cdr p) "nhom") "\t" (bht:get (cdr p) "ly_trinh_km") "\t" (bht:get (cdr p) "station_status") "\t" (bht:get (cdr p) "field_last_error")) qa-f))
  (close qa-f)
  (setq qa-f (open (strcat qa-dir "/snapshot.txt") "w" "utf8"))
  (write-line (vl-prin1-to-string (qa103-snapshot)) qa-f) (close qa-f))
 (progn
  (setq qa-f (open (strcat qa-dir "/snapshot.txt") "r" "utf8") qa-expected (read (read-line qa-f))) (close qa-f)
  (setq qa-actual (qa103-snapshot) qa-i 0)
  (foreach label '("points" "symbols" "records" "method" "marker groups")
   (qa103-check (strcat "reopen " label) (equal (nth qa-i qa-expected) (nth qa-i qa-actual) 1e-9))
   (setq qa-i (1+ qa-i)))
  (setq qa-f (open (strcat qa-dir "/snapshot-reopen.txt") "w" "utf8-bom"))
  (write-line (vl-prin1-to-string qa-actual) qa-f) (close qa-f)))
(close qa-log)
(princ "\nSAMPLE103-COMPLETE")
(princ)
