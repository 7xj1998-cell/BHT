(setq l129-fails 0)
(defun l129-check (name ok)
  (if (not ok) (setq l129-fails (1+ l129-fails)))
  (princ (strcat "\n" (if ok "PASS L129 " "FAIL L129 ") name)))
(setq *bht-caption-rec* '(("object_id" . "LABEL-QA") ("nhom" . "BIEN_BAO") ("ma_hieu" . "W.239a")
  ("mat" . "W.239a") ("mat" . "S.509a@5") ("ly_trinh_km" . "Km48+530.05")))
(bht:meta-set "sign_label_orientation" "PARALLEL")
(setq bend (entmakex '((0 . "LWPOLYLINE") (100 . "AcDbEntity") (100 . "AcDbPolyline") (90 . 3) (70 . 0) (38 . 0.0)
                       (10 0.0 0.0) (10 20.0 0.0) (10 20.0 -3.0))))
(entmod (append (entget bend) (list (list -3 (list "BHT_KH" '(1000 . "LABEL-QA") '(1000 . "DAN") '(1000 . "ONE"))))))
(setq *bht-caption-leaders* (list (list "LABEL-QA" bend)))
(foreach h '(0.369 1.107 2.214)
  (setq layout (bht:kh-caption-leader-layout (list '(0.0 0.0 0.0) h) '((20.0 -3.0 0.0) 1.0 0.0))
        title (car layout) rot (caddr layout)
        auxiliary (polar title (- rot (/ pi 2.0)) (* 1.5 h))
        station (polar title (- rot (/ pi 2.0)) (* 3.0 h)))
  (l129-check "long-run-not-short-return" (equal rot 0.0 1e-8))
  (l129-check "all-rows-centered" (and (equal (car title) 10.0 1e-8) (equal (car auxiliary) 10.0 1e-8) (equal (car station) 10.0 1e-8)))
  (l129-check "both-code-rows-above-leader" (> (- (cadr auxiliary) h) 0.0))
  (l129-check "chainage-below-leader" (< (cadr station) 0.0))
  (l129-check "equal-clearance-around-leader" (equal (- (cadr auxiliary) h) (- (cadr station)) 1e-8)))
(entdel bend)
(setq *bht-caption-rec* nil *bht-caption-leaders* nil)
(setq title (car (vl-remove-if 'bht:kh-extra-label-p
  (mapcar 'cdr (vl-remove-if-not '(lambda (p) (= (car p) "LABEL-TWO")) (bht:tagged-pairs "TEXT" "BHT_KH" 1))))))
(setq l129-before-sign (entget sign) l129-before-rec (bht:obj-read "LABEL-TWO"))
(bht:kh-display-transaction 'bht:kh-caption-template (list '("LABEL-TWO")))
(l129-check "template-repositions-manual-label-only" (and (equal l129-before-sign (entget sign))
  (equal l129-before-rec (bht:obj-read "LABEL-TWO"))
  (not (equal manual-point (cdr (assoc 11 (entget title))) 1e-8))))
(princ (strcat "\nL129-FAIL=" (itoa l129-fails)))
