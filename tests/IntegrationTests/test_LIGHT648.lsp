;; Regression: update a pre-0.6.48 INSERT and its BHT label without touching survey text.
(foreach oid '("LIGHT-OBJ" "LIGHT-DEN_CS" "LIGHT-DEN_TH")
  (setq rec (bht:obj-read oid)
        inserted (cdr (assoc oid (bht:tagged-pairs "INSERT" "BHT_KH" 1)))
        d (entget inserted) pos (cdr (assoc 10 d)) rot (cdr (assoc 50 d))
        oldsc 4.0)
  (entmod (append (bht:dxf-put (bht:dxf-put (bht:dxf-put d 41 oldsc) 42 oldsc) 43 oldsc)
    (list (bht:kh-xdata-ins oid "TU_DONG" pos rot oldsc))))
  (setq stale (entmakex (append (list '(0 . "TEXT") '(8 . "BHT_NHAN") (cons 10 pos)
    '(40 . 0.35) '(1 . "Old light label")) (list (bht:kh-xdata-txt oid "TU_DONG" pos)))))
  (light-check (strcat oid "-old-label-created") stale)
  (bht:symbol-sync (list oid))
  (setq d (entget inserted))
  (light-check (strcat oid "-normalized-scale") (equal (cdr (assoc 41 d)) (bht:kh-scale-for rec) 1e-8))
  (light-check (strcat oid "-position-rotation-preserved") (and (equal pos (cdr (assoc 10 d)) 1e-8) (equal rot (cdr (assoc 50 d)) 1e-8)))
  (light-check (strcat oid "-old-label-removed") (null (entget stale)))
  (light-check (strcat oid "-no-new-label") (null (assoc oid (bht:tagged-pairs "TEXT" "BHT_KH" 1))))
  (bht:symbol-sync (list oid))
  (light-check (strcat oid "-repeat-idempotent") (equal d (entget inserted))))
(light-check "light-update-keeps-survey" (equal light-before (entget light-p '("BHT_PT"))))
(light-check "sign-scale-unchanged" (equal (bht:kh-scale-for '(("nhom" . "BIEN_BAO"))) (bht:sign-scale) 1e-8))
(light-check "marker-scale-unchanged" (equal (bht:kh-scale-for '(("nhom" . "COC_TIEU"))) (bht:kh-scale) 1e-8))
(setq rec '(("nhom" . "DEN_CS")))
(light-check "light-auto-gap-unchanged" (equal (bht:kh-auto-transform rec '(100.0 100.0 0.0) (bht:kh-scale-for rec))
  (bht:kh-route-transform rec '(100.0 100.0 0.0) (bht:kh-scale)) 1e-8))
