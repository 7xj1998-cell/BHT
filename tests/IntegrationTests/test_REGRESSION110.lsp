(setq qa110-fails 0)
(defun qa110-check (name ok)
  (if (not ok) (setq qa110-fails (1+ qa110-fails)))
  (princ (strcat "\n" (if qa110-baseline "BASELINE " (if ok "PASS " "FAIL ")) "QA110 " name "=" (if ok "OK" "FAILED"))))
(bht:api-messages "CLEAR")
(setq qa110-i 0)
(repeat 180 (bht:screen-message-add (strcat "COC-" (itoa (setq qa110-i (1+ qa110-i))))))
(setq qa110-messages (cdr (bht:api-messages "DRAIN")))
(qa110-check "report-keeps-all-180-stakes" (and (= (length qa110-messages) 180) (= (car qa110-messages) "COC-1") (= (last qa110-messages) "COC-180")))
(qa110-check "report-drain" (equal (bht:api-messages "PEEK") '("OK")))
(setq qa110-line (entmakex '((0 . "LWPOLYLINE") (100 . "AcDbEntity") (100 . "AcDbPolyline") (90 . 2) (70 . 0) (10 0.0 0.0) (10 100.0 0.0))))
(bht:route-create "QA110-START" qa110-line "TIM_DUONG" 50.0 0.0 1 "QA")
(setq qa110-route (bht:route-read "QA110-START"))
(setq qa110-result (bht:route-set-start-dir "QA110-START" '(0.0 500.0 0.0) 1))
(qa110-check "far-start-rejected-without-write" (and (null (car qa110-result)) (equal qa110-route (bht:route-read "QA110-START"))))
(bht:route-write "QA110-START" qa110-route)
(setq qa110-result (bht:route-set-start-dir "QA110-START" '(100.0 0.0 0.0) 1))
(qa110-check "outward-direction-rejected-without-write" (and (null (car qa110-result)) (equal qa110-route (bht:route-read "QA110-START"))))
(bht:route-write "QA110-START" qa110-route)
(qa110-check "valid-start-accepted" (car (bht:route-set-start-dir "QA110-START" '(0.0 0.0 0.0) 1)))
(bht:route-add-mark "QA110-START" 0.0 1000.0 1000.0 "QA" "")
(bht:route-add-mark "QA110-START" 100.0 1100.0 1100.0 "QA" "")
(setq qa110-route (bht:route-read "QA110-START"))
(qa110-check "existing-marks-block-rebased-start" (and (not (car (bht:route-set-start-dir "QA110-START" '(20.0 0.0 0.0) 1))) (equal qa110-route (bht:route-read "QA110-START"))))
(setq qa110-point (entmakex '((0 . "POINT") (10 50.0 2.0 0.0))))
(bht:pt-write-xdata qa110-point "QA110-P" "QA" "1" "1" 50.0 2.0 0.0 "" "" "" "")
(bht:obj-create "QA110-OBJ" '(("nhom" . "BIEN_BAO") ("ma_hieu" . "P.102") ("phia_duong" . "TRAI")) '("QA110-P") T)
(bht:rec-write "SEG" "QA110-SEG" '(("segment_id" . "QA110-SEG") ("package_id" . "QA") ("km_start_m" . "1000") ("km_end_m" . "1100") ("side" . "HAI_BEN") ("route_id" . "QA110-START")))
(defun BHTPROGRESSPREVIEW (title rows) "PENDING")
(setq qa110-before (list (bht:rec-all "OBJ") (bht:rec-all "SEG") (bht:rec-all "ROUTE") (bht:pt-all)))
(bht:progress-preview-open "QA110" (bht:progress-plan "QA110-SEG" "QA110-START"))
(setq qa110-token (car *bht-progress-pending*))
(qa110-check "modeless-preview-stores-no-dwg-change" (equal qa110-before (list (bht:rec-all "OBJ") (bht:rec-all "SEG") (bht:rec-all "ROUTE") (bht:pt-all))))
(bht:obj-write "QA110-OBJ" (bht:set (bht:obj-read "QA110-OBJ") "ma_hieu" "P.103a"))
(setq qa110-before (bht:rec-all "OBJ"))
(qa110-check "modeless-stale-plan-rejected" (and (= (car (bht:api-progress-preview-apply qa110-token)) "LOI") (equal qa110-before (bht:rec-all "OBJ"))))
(bht:progress-preview-open "QA110" (bht:progress-plan "QA110-SEG" "QA110-START"))
(setq qa110-token (car *bht-progress-pending*))
(qa110-check "modeless-fresh-plan-applies" (and (= (car (bht:api-progress-preview-apply qa110-token)) "OK") (= (bht:get (bht:obj-read "QA110-OBJ") "ly_trinh_m") "1050.000")))
(setq qa110-before (bht:rec-all "OBJ"))
(qa110-check "modeless-token-single-use" (and (= (car (bht:api-progress-preview-apply qa110-token)) "LOI") (equal qa110-before (bht:rec-all "OBJ"))))
(bht:rec-delete "ROUTE" "QA110-START") (entdel qa110-line)
(princ (strcat "\nQA110-DONE FAIL=" (itoa qa110-fails)))
(princ)
