(setq a114-before (list (bht:rec-all "OBJ") (bht:rec-all "SEG") (bht:rec-all "ROUTE") (bht:pt-all))
      a114-index (bht:pt-all) a114-count 0 a114-d11 0
      a114-file (open (strcat (getvar "DWGPREFIX") "scope-audit.tsv") "w"))
(write-line "object\tsegment\troute\tlocked\tstored_station\tstored_status\tnew_status\tnew_station\tnote" a114-file)
(foreach a114-p (bht:rec-all "OBJ")
  (setq a114-rec (cdr a114-p) a114-route (bht:route-read (bht:get a114-rec "route_id"))
        a114-pos (bht:obj-position a114-rec a114-index) a114-result nil)
  (if (bht:progress-locked a114-rec) (progn (setq a114-count (1+ a114-count)) (if (= "DOAN_11" (bht:get a114-rec "doan")) (setq a114-d11 (1+ a114-d11)))))
  (if (and a114-route a114-pos) (setq a114-result (bht:station-object-route a114-route a114-rec a114-index a114-pos)))
  (write-line (bht:join (list (car a114-p) (bht:get a114-rec "doan") (bht:get a114-rec "route_id") (bht:get a114-rec "progress_locked")
    (bht:get a114-rec "ly_trinh_m") (bht:get a114-rec "station_status") (bht:str (cdr (assoc 'status a114-result)))
    (bht:str (cdr (assoc 'station a114-result))) (bht:str (cdr (assoc 'note a114-result)))) (chr 9)) a114-file))
(close a114-file)
(princ (strcat "\nPASS SCOPE114 REAL count=" (itoa (length (bht:rec-all "OBJ"))) " locked=" (itoa a114-count) " D11-locked=" (itoa a114-d11)))
(princ (if (equal a114-before (list (bht:rec-all "OBJ") (bht:rec-all "SEG") (bht:rec-all "ROUTE") (bht:pt-all))) "\nPASS SCOPE114 REAL canonical-unchanged" "\nFAIL SCOPE114 REAL mutated"))
(princ "\nQA110-DONE")
(princ)
