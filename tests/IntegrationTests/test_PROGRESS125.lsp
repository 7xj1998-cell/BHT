(setq p125-n 0 p125-fail 0)
(defun p125-check (name ok) (setq p125-n (1+ p125-n)) (if (not ok) (setq p125-fail (1+ p125-fail))) (princ (strcat "\n" (if ok "PASS PROGRESS125 " "FAIL PROGRESS125 ") name)))
(defun p125-route (id x km / ent)
 (setq ent (entmakex (list '(0 . "LWPOLYLINE") '(100 . "AcDbEntity") '(100 . "AcDbPolyline") '(90 . 2) '(70 . 0) (cons 10 (list x 0.0)) (cons 10 (list (+ x 100.0) 0.0)))))
 (bht:route-create id ent "TIM_RANH" 10.0 0.0 nil "QA") (bht:route-add-mark id 0.0 km km "QA" "") (bht:route-add-mark id 100.0 (+ km 100.0) (+ km 100.0) "QA" ""))
(defun p125-obj (id x / ent pid)
 (setq ent (entmakex (list '(0 . "POINT") (cons 10 (list x 2.0 0.0)))) pid (strcat id "-P"))
 (bht:pt-write-xdata ent pid "QA" "1" id 2.0 x 0.0 "BIEN_BAO" "QA" "" "")
 (bht:obj-create id '(("nhom" . "BIEN_BAO") ("ma_hieu" . "W.207a") ("phia_duong" . "TRAI")) (list pid) T))
(p125-route "R10" 0.0 1000.0) (p125-route "R11" 100.0 1100.0)
(bht:rec-write "SEG" "D10" '(("segment_id" . "D10") ("package_id" . "G1") ("package_name" . "DT.830") ("km_start_m" . "1000") ("km_end_m" . "1100") ("side" . "HAI_BEN") ("route_id" . "")))
(bht:rec-write "SEG" "D11" '(("segment_id" . "D11") ("package_id" . "G2") ("package_name" . "DT.830") ("km_start_m" . "1100") ("km_end_m" . "1200") ("side" . "HAI_BEN") ("route_id" . "")))
(p125-obj "A10" 50.0) (p125-obj "B11" 150.0) (p125-obj "OUT" 250.0)
(setq p125-other (bht:obj-read "B11") p125-out (bht:obj-read "OUT") p125-plan (bht:progress-plan "D10" "R10"))
(p125-check "preview-selects-only-in-range-unfinished-object" (and (= (length (nth 2 p125-plan)) 1) (= (caar (nth 2 p125-plan)) "A10")))
(p125-check "preview-does-not-write" (and (= (bht:get (bht:obj-read "A10") "ly_trinh_m") "") (equal p125-other (bht:obj-read "B11"))))
(setq p125-result (bht:progress-apply p125-plan))
(p125-check "segment10-computed" (and (car p125-result) (= (bht:get (bht:obj-read "A10") "ly_trinh_m") "1050.000") (= (bht:get (bht:obj-read "A10") "doan") "D10")))
(p125-check "outside-objects-unchanged" (and (equal p125-other (bht:obj-read "B11")) (equal p125-out (bht:obj-read "OUT"))))
(setq p125-result (bht:kh-display-transaction 'bht:progress-finish (list "D10")))
(p125-check "segment10-confirmed" (and (not (eq (car p125-result) 'LOI)) (bht:progress-locked (bht:obj-read "A10"))))
(setq p125-a (bht:obj-read "A10"))
(BHT125STAGEEXPORT)
(bht:progress-apply (bht:progress-plan "D11" "R11"))
(p125-check "segment11-computed-without-overwriting10" (and (= (bht:get (bht:obj-read "B11") "ly_trinh_m") "1150.000") (equal p125-a (bht:obj-read "A10"))))
(bht:station-objects) (bht:route-recalculate "R11") (bht:assign-segments)
(p125-check "legacy-bulk-calculation-preserves-confirmed10" (equal p125-a (bht:obj-read "A10")))
(setq p125-result (vl-catch-all-apply 'bht:obj-write (list "A10" (bht:set p125-a "ly_trinh_m" "0"))))
(p125-check "confirmed-station-cannot-be-overwritten" (and (vl-catch-all-error-p p125-result) (equal p125-a (bht:obj-read "A10"))))
(p125-check "confirmed-segment-allows-empty-incremental-plan" (and (not (eq (car (bht:progress-plan "D10" "R10")) 'LOI)) (null (nth 2 (bht:progress-plan "D10" "R10")))))
(bht:kh-display-transaction 'bht:progress-reopen (list "D10"))
(p125-check "reopen-preserves-number-unlocks-only-segment" (and (not (bht:progress-locked (bht:obj-read "A10"))) (= (bht:get (bht:obj-read "A10") "ly_trinh_m") "1050.000")))
(bht:progress-apply (bht:progress-plan "D10" "R10")) (bht:kh-display-transaction 'bht:progress-finish (list "D10"))
(bht:progress-apply (bht:progress-plan "D11" "R11")) (bht:kh-display-transaction 'bht:progress-finish (list "D11"))
(p125-check "both-segments-confirmed" (and (bht:progress-locked (bht:obj-read "A10")) (bht:progress-locked (bht:obj-read "B11"))))
(setq p125-a (bht:rec-all "OBJ") p125-routes (bht:rec-all "ROUTE"))
(setq p125-result (vl-catch-all-apply 'bht:route-edit (list "R10" "RENAMED" "TIM_RANH" 10.0 0.0)))
(p125-check "confirmed-route-rename-blocked-before-creating-new-route" (and (vl-catch-all-error-p p125-result) (equal p125-routes (bht:rec-all "ROUTE")) (equal p125-a (bht:rec-all "OBJ"))))
(setq p125-result (vl-catch-all-apply 'bht:route-delete (list "R10")))
(p125-check "confirmed-route-delete-blocked-before-changing-objects" (and (vl-catch-all-error-p p125-result) (equal p125-routes (bht:rec-all "ROUTE")) (equal p125-a (bht:rec-all "OBJ"))))
(princ (strcat "\nPROGRESS125-LISP=" (itoa p125-n) " FAIL=" (itoa p125-fail))) (princ)
