(defun qa132-eval (expression / result)
  (setq result (vl-catch-all-apply '(lambda () (eval (read expression))) nil))
  (if (vl-catch-all-error-p result) (list "LOI" (vl-catch-all-error-message result)) (list "OK" (vl-prin1-to-string result))))
(vl-acad-defun 'qa132-eval)
(defun qa132-unrelated (id / ss i e out)
  (setq ss (ssget "_X") i 0)
  (if ss (repeat (sslength ss)
    (setq e (ssname ss i) i (1+ i))
    (if (and (/= (car (bht:xget e "BHT_KH")) id) (/= (car (bht:xget e "BHT_SIGN_ORIGIN")) id))
      (setq out (cons (vl-prin1-to-string (entget e '("*"))) out)))))
  (cons "OK" (reverse out)))
(vl-acad-defun 'qa132-unrelated)
(princ)
