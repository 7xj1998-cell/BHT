(setq qa110-fails 0)
(defun qa110-check (name ok)
  (if (not ok) (setq qa110-fails (1+ qa110-fails)))
  (princ (strcat "\n" (if qa110-baseline "BASELINE " (if ok "PASS " "FAIL ")) "QA110 " name "=" (if ok "OK" "FAILED"))))
(bht:regapp "BHT_KH")
(setq qa110-point (entmakex '((0 . "POINT") (10 50.0 4.0 0.0))))
(bht:pt-write-xdata qa110-point "CAP110-PT" "QA" "1" "1" 50.0 4.0 0.0 "" "" "" "")
(setq qa110-line (entmakex '((0 . "LWPOLYLINE") (100 . "AcDbEntity") (100 . "AcDbPolyline") (90 . 2) (70 . 0) (10 0.0 0.0) (10 100.0 0.0))))
(bht:route-create "CAP110" qa110-line "TIM_DUONG" 50.0 0.0 1 "QA")
(bht:route-write "CAP110" (bht:set-all (bht:route-read "CAP110") "moc" '("0|1100|1100|QA|" "100|1000|1000|QA|")))
(setq *bht-caption-rec* '(("object_id" . "CAP110") ("nhom" . "BIEN_BAO") ("route_id" . "CAP110") ("pt" . "CAP110-PT") ("ma_hieu" . "W.239a") ("mat" . "W.239a") ("mat" . "S.509a@5") ("ly_trinh_km" . "Km1+050")))
(setq qa110-leader (entmakex '((0 . "LINE") (10 50.0 4.0 0.0) (11 50.0 24.0 0.0))))
(entmod (append (entget qa110-leader) (list (list -3 (list "BHT_KH" '(1000 . "CAP110") '(1000 . "DAN") '(1000 . "CAP110-PT"))))))
(setq *bht-caption-leaders* (list (list "CAP110" qa110-leader)))
(bht:meta-set "sign_label_orientation" "PARALLEL")
(setq qa110-layout (bht:kh-caption-leader-layout '((50.0 24.0 0.0) 0.369) '((50.0 24.0 0.0) 1.0 0.0)))
(qa110-check "negative-km-label-reads-in-route-frame" (> (sin (caddr qa110-layout)) 0.99999))
(bht:route-write "CAP110" (bht:set-all (bht:route-read "CAP110") "moc" '("0|1000|1000|QA|" "100|1100|1100|QA|")))
(setq qa110-layout (bht:kh-caption-leader-layout '((50.0 24.0 0.0) 0.369) '((50.0 24.0 0.0) 1.0 0.0)))
(qa110-check "positive-km-label-reads-in-route-frame" (< (sin (caddr qa110-layout)) -0.99999))
(setq qa110-before qa110-layout)
(command-s "_.UCS" "_Z" "37")
(setq qa110-layout (bht:kh-caption-leader-layout '((50.0 24.0 0.0) 0.369) '((50.0 24.0 0.0) 1.0 0.0)))
(qa110-check "rotated-ucs-same-wcs-layout" (equal qa110-layout qa110-before 1e-8))
(command-s "_.UCS" "_World")
(if (not qa110-baseline)
  (progn
    (bht:route-write "CAP110" (bht:set-all (bht:route-read "CAP110") "moc" '("0|1000|1000|QA|" "50|1050|1050|QA|" "100|1000|1000|QA|")))
    (qa110-check "opposing-chainage-at-mark-has-no-guessed-heading" (null (bht:kh-caption-route-angle *bht-caption-rec*)))
    (bht:route-write "CAP110" (bht:set-all (bht:route-read "CAP110") "moc" '("0|1000|1000|QA|" "50|1050|2000|QA|" "100|2050|2050|QA|")))
    (qa110-check "same-direction-station-equation-has-heading" (equal (bht:kh-caption-route-angle *bht-caption-rec*) 0.0 1e-8))
    (setq qa110-layout-count 0)
    (foreach qa110-deg '(0 45 90 135 180 225 270 315)
      (foreach qa110-order '(1 -1)
        (foreach qa110-km '(1 -1)
          (foreach qa110-side '(1 -1)
            (setq qa110-a (* pi (/ qa110-deg 180.0))
                  qa110-t (list (cos qa110-a) (sin qa110-a) 0.0) qa110-normal (list (- (sin qa110-a)) (cos qa110-a) 0.0)
                  qa110-end (mapcar '(lambda (v) (* v 100.0)) qa110-t)
                  qa110-source (mapcar '+ (mapcar '(lambda (v) (* v 50.0)) qa110-t) (mapcar '(lambda (v) (* qa110-side v 4.0)) qa110-normal)))
            (entmod (append (vl-remove-if '(lambda (p) (= (car p) 10)) (entget qa110-line))
              (list (cons 10 (if (= qa110-order 1) '(0.0 0.0) (list (car qa110-end) (cadr qa110-end))))
                    (cons 10 (if (= qa110-order 1) (list (car qa110-end) (cadr qa110-end)) '(0.0 0.0))))))
            (entmod (bht:dxf-put (entget qa110-point) 10 qa110-source))
            (setq qa110-rec (bht:route-read "CAP110")
                  qa110-rec (bht:set qa110-rec "geometry_signature" (bht:route-geometry-signature qa110-line 0.0 1))
                  qa110-rec (bht:set-all qa110-rec "moc" (if (= (* qa110-order qa110-km) 1) '("0|1000|1000|QA|" "100|1100|1100|QA|") '("0|1100|1100|QA|" "100|1000|1000|QA|"))))
            (bht:route-write "CAP110" qa110-rec)
            (entmod (bht:dxf-put (bht:dxf-put (entget qa110-leader) 10 qa110-source) 11
              (mapcar '+ qa110-source (mapcar '(lambda (v) (* qa110-side v 20.0)) qa110-normal))))
            (foreach qa110-mode '("PARALLEL" "PERPENDICULAR")
              (bht:meta-set "sign_label_orientation" qa110-mode)
              (setq qa110-layout (bht:kh-caption-leader-layout (list qa110-source 0.369) (list qa110-source 1.0 0.0))
                    qa110-heading (+ qa110-a (if (= qa110-km 1) 0.0 pi))
                    qa110-expected (+ qa110-a (if (= qa110-mode "PARALLEL") (/ pi 2.0) pi)))
              (qa110-check (strcat "route-axis-" (itoa qa110-layout-count))
                (and (numberp (bht:kh-caption-route-angle *bht-caption-rec*))
                     (> (cos (- (bht:kh-caption-route-angle *bht-caption-rec*) qa110-heading)) 0.999999)
                     (< (abs (sin (- (caddr qa110-layout) qa110-expected))) 1e-7)
                     (>= (cos (- (caddr qa110-layout) (- qa110-heading (/ pi 2.0)))) -1e-7)))
              (qa110-check (strcat "repeat-label-" (itoa qa110-layout-count))
                (equal qa110-layout (bht:kh-caption-leader-layout (list qa110-source 0.369) (list qa110-source 1.0 0.0)) 1e-8))
              (setq qa110-layout-count (1+ qa110-layout-count)))))))
    ;; A true arc uses its local derivative, not the endpoint chord.
    (entmod (append (vl-remove-if '(lambda (p) (member (car p) '(10 42))) (entget qa110-line)) '((10 0.0 0.0) (42 . 0.41421356237) (10 100.0 0.0) (42 . 0.0))))
    (setq qa110-length (bht:curve-length qa110-line)
          qa110-cp (vlax-curve-getPointAtDist qa110-line (* qa110-length 0.3))
          qa110-der (vlax-curve-getFirstDeriv qa110-line (vlax-curve-getParamAtPoint qa110-line qa110-cp))
          qa110-a (atan (cadr qa110-der) (car qa110-der))
          qa110-source (mapcar '+ qa110-cp (list (* -4.0 (sin qa110-a)) (* 4.0 (cos qa110-a)) 0.0)))
    (entmod (bht:dxf-put (entget qa110-point) 10 qa110-source))
    (bht:route-write "CAP110" (bht:set-all (bht:set (bht:route-read "CAP110") "geometry_signature" (bht:route-geometry-signature qa110-line 0.0 1)) "moc"
      (list "0|1000|1000|QA|" (strcat (rtos qa110-length 2 8) "|" (rtos (+ 1000.0 qa110-length) 2 8) "|" (rtos (+ 1000.0 qa110-length) 2 8) "|QA|"))))
    (qa110-check "curved-route-local-tangent" (and (numberp (bht:kh-caption-route-angle *bht-caption-rec*))
      (> (cos (- qa110-a (bht:kh-caption-route-angle *bht-caption-rec*))) 0.999999)))
    (setq qa110-point2 (entmakex (list '(0 . "POINT") (cons 10 (mapcar '+ qa110-source '(0.0 1.0 0.0))))))
    (bht:pt-write-xdata qa110-point2 "CAP110-PT2" "QA" "1" "2" (car qa110-source) (1+ (cadr qa110-source)) 0.0 "" "" "" "")
    (setq *bht-caption-rec* (bht:set-all (bht:set *bht-caption-rec* "so_tru" "2") "pt" '("CAP110-PT" "CAP110-PT2")))
    (setq qa110-rtk-before (bht:pt-all) qa110-route-before (bht:rec-all "ROUTE"))
    (bht:obj-create "CAP110" *bht-caption-rec* '("CAP110-PT") T)
    (bht:obj-write "CAP110" (bht:set (bht:set *bht-caption-rec* "so_mat" "2") "so_tru" "2"))
    (bht:symbol-sync '("CAP110"))
    (setq qa110-insert (cdr (assoc "CAP110" (bht:tagged-pairs "INSERT" "BHT_KH" 1)))
          qa110-insert-before (entget qa110-insert '("*")) qa110-obj-before (bht:obj-read "CAP110"))
    (setq qa110-texts (mapcar 'cdr (bht:tagged-pairs "TEXT" "BHT_KH" 1))
          qa110-title (car (vl-remove-if 'bht:kh-extra-label-p qa110-texts)))
    (qa110-check "actual-three-caption-rows" (= (length qa110-texts) 3))
    (setq qa110-text-before (mapcar '(lambda (e) (entget e '("*"))) qa110-texts))
    (bht:kh-layout-refresh '("CAP110"))
    (qa110-check "actual-sync-idempotent" (equal qa110-text-before (mapcar '(lambda (e) (entget e '("*"))) qa110-texts) 1e-8))
    (command-s "_.UCS" "_Z" "37") (command-s "_.PLAN" "_Current")
    (bht:kh-layout-refresh '("CAP110"))
    (qa110-check "actual-ucs-view-does-not-change-text" (equal qa110-text-before (mapcar '(lambda (e) (entget e '("*"))) qa110-texts) 1e-8))
    (command-s "_.UCS" "_World") (command-s "_.PLAN" "_World")
    (entmod (bht:dxf-put (entget qa110-title) 50 0.123))
    (setq qa110-manual-angle (cdr (assoc 50 (entget qa110-title))))
    (bht:kh-layout-refresh '("CAP110"))
    (qa110-check "rotate-only-manual-primary-kept" (equal qa110-manual-angle (cdr (assoc 50 (entget qa110-title))) 1e-8))
    (setq qa110-extra (car (vl-remove-if-not 'bht:kh-extra-face-label-p qa110-texts)))
    (entmod (bht:dxf-put (bht:dxf-put (entget qa110-extra) 10 '(500.0 600.0 0.0)) 11 '(500.0 600.0 0.0)))
    (setq qa110-manual-extra (entget qa110-extra '("*")))
    (bht:kh-layout-refresh '("CAP110"))
    (qa110-check "manual-auxiliary-kept" (equal qa110-manual-extra (entget qa110-extra '("*"))))
    (bht:kh-caption-template '("CAP110"))
    (qa110-check "explicit-template-resets-manual-cluster" (not (equal qa110-manual-extra (entget qa110-extra '("*")))))
    (qa110-check "caption-only-keeps-block-rtk-route-record" (and (equal qa110-insert-before (entget qa110-insert '("*")))
      (equal qa110-rtk-before (bht:pt-all)) (equal qa110-route-before (bht:rec-all "ROUTE")) (equal qa110-obj-before (bht:obj-read "CAP110"))))))
(princ (strcat "\nQA110-DONE FAIL=" (itoa qa110-fails)))
(princ)
