(setq review113-fails 0)
(defun review113-check (name ok)
  (if (not ok) (setq review113-fails (1+ review113-fails)))
  (princ (strcat "\n" (if ok "PASS " "FAIL ") "REVIEW113 " name)))
(review113-check "reject-overfull-metres" (null (bht:parse-km "Km1+1000")))
(review113-check "reject-negative-input" (null (bht:parse-km "-1")))
(review113-check "reject-unrepresentable-km" (null (bht:parse-km "2147483648000")))
(review113-check "normal-comma-input" (equal (bht:parse-km "Km39+050,5") 39050.5 1e-8))
(review113-check "normal-rounding" (= (bht:fmt-km 999.999) "Km1+000.00"))
(foreach review113-distance '(0.0 50.0 -10.0)
  (setq review113-result (vl-catch-all-apply 'bht:km-from-dist
    (list '((0.0 1000.0 1000.0) (0.0 1100.0 1100.0)) review113-distance 100.0 1)))
  (review113-check (strcat "duplicate-controls-" (rtos review113-distance 2 0))
    (and (not (vl-catch-all-error-p review113-result)) (null (cadr review113-result)))))
(setq review113-result (bht:km-from-dist '((0.0 1000.0 1000.0) (100.0 1100.0 1200.0) (200.0 1300.0 1300.0)) 150.0 0.0 1))
(review113-check "station-break-retained" (equal (cadr review113-result) 1250.0 1e-8))
(setq review113-result (bht:km-from-dist '((0.0 1000.0 1000.0) (100.0 1100.0 1100.0)) 50.0 0.0 1))
(review113-check "normal-interpolation" (equal (cadr review113-result) 1050.0 1e-8))
(princ (strcat "\nREVIEW113-FAIL=" (itoa review113-fails)))
(princ)
