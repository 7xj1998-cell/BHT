(setq sm114-points (bht:pt-all) sm114-routes (bht:rec-all "ROUTE") sm114-objs (bht:rec-all "OBJ")
      sm114-tim (bht:route-read "TUYEN1") sm114-fails 0 sm114-markers 0 sm114-oriented 0)
(if (null sm114-tim) (setq sm114-tim (cdar sm114-routes)))
(setq sm114-id (bht:get sm114-tim "route_id"))
(if (= sm114-id "") (setq sm114-id (caar sm114-routes)))
(setq sm114-ent (bht:route-ent (bht:route-read sm114-id))
      sm114-start (getvar "MILLISECS") sm114-result (bht:api-symbol-center sm114-id "20" "GAP_KHUC"))
(princ sm114-result)
(if (/= (car sm114-result) "OK") (setq sm114-fails (1+ sm114-fails)))
(foreach pair (bht:tagged-pairs "INSERT" "BHT_KH" 1)
  (setq id (car pair) rec (bht:obj-read id) d (entget (cdr pair)))
  (if (and (= (bht:get rec "nhom") "COC_TIEU") (setq pt (bht:obj-position rec sm114-points))
           (not (bht:kh-marker-locked-p id)))
    (progn
      (setq sm114-markers (1+ sm114-markers))
      (if (or (not (equal pt (cdr (assoc 10 d)) 1e-7))
              (assoc id (bht:tagged-pairs "LINE" "BHT_KH" 1))
              (assoc id (bht:tagged-pairs "LWPOLYLINE" "BHT_KH" 1)))
        (setq sm114-fails (1+ sm114-fails)))
      (setq frame (bht:kh-road-frame sm114-ent pt 1))
      (if (and frame (not (nth 4 frame)))
        (progn
          (setq sm114-oriented (1+ sm114-oriented) n (cadr frame) rot (cdr (assoc 50 d)))
          (if (> (abs (- (* (cos rot) (cadr n)) (* (sin rot) (car n)))) 1e-7)
            (setq sm114-fails (1+ sm114-fails))))))))
(foreach pair sm114-objs
  (setq before (cdr pair) after (bht:obj-read (car pair)))
  (foreach key '("route_id" "ly_trinh_m" "ly_trinh_km" "marker_h" "marker_km" "nguon_km" "station_status" "phia_tuyen" "phia_duong" "field_chain_id" "goi" "doan")
    (if (/= (bht:get before key) (bht:get after key)) (setq sm114-fails (1+ sm114-fails)))))
(if (or (not (equal sm114-points (bht:pt-all))) (not (equal sm114-routes (bht:rec-all "ROUTE"))))
  (setq sm114-fails (1+ sm114-fails)))
(princ (strcat "\nSAMPLE-MARKER114 markers=" (itoa sm114-markers) " oriented=" (itoa sm114-oriented)
  " ms=" (itoa (- (getvar "MILLISECS") sm114-start)) " FAIL=" (itoa sm114-fails)))
(princ)
