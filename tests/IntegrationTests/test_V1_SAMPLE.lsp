(setq v1-folder (getenv "BHT_V1_QA"))
(setq v1-file (open (strcat v1-folder "/points-before.txt") "w" "utf8-bom"))
(foreach item (bht:pt-all)
 (write-line (vl-prin1-to-string (list (car item) (mapcar '(lambda (v) (rtos v 2 12)) (bht:pv (cdr item) 'xyz)) (bht:pv (cdr item) 'src) (bht:pv (cdr item) 'n) (bht:pv (cdr item) 'e))) v1-file))
(close v1-file)
(setq v1-file (open (strcat v1-folder "/sample-check.txt") "w" "utf8-bom"))
(foreach line (bht:api-check) (write-line line v1-file))
(write-line (strcat "station_method=" (bht:meta "station_method" "ROUTE")) v1-file)
(write-line (strcat "field_active_chain=" (bht:meta "field_active_chain" "")) v1-file)
(foreach item (bht:rec-all "FIELD_CHAIN") (write-line (vl-prin1-to-string item) v1-file))
(close v1-file)
(setq v1-file (open (strcat v1-folder "/field-before.txt") "w" "utf8-bom"))
(foreach item (bht:rec-all "OBJ") (write-line (vl-prin1-to-string item) v1-file))
(close v1-file)
(setq v1-times nil)
(repeat 5
 (setq v1-start (getvar "MILLISECS"))
 (setq v1-result (bht:field-objects))
 (setq v1-times (append v1-times (list (- (getvar "MILLISECS") v1-start)))))
(setq v1-file (open (strcat v1-folder "/field-perf.txt") "w" "utf8-bom"))
(write-line (strcat "milliseconds=" (vl-prin1-to-string v1-times)) v1-file)
(write-line (strcat "result=" (vl-prin1-to-string v1-result)) v1-file)
(close v1-file)
(setq v1-file (open (strcat v1-folder "/field-after.txt") "w" "utf8-bom"))
(foreach item (bht:rec-all "OBJ") (write-line (vl-prin1-to-string item) v1-file))
(close v1-file)
(princ "\nV1-SAMPLE-COMPLETE")
(setq v1-file (open (strcat v1-folder "/points-after.txt") "w" "utf8-bom"))
(foreach item (bht:pt-all)
 (write-line (vl-prin1-to-string (list (car item) (mapcar '(lambda (v) (rtos v 2 12)) (bht:pv (cdr item) 'xyz)) (bht:pv (cdr item) 'src) (bht:pv (cdr item) 'n) (bht:pv (cdr item) 'e))) v1-file))
(close v1-file)
