(vl-load-com)
(setq *sign-test-fail* 0)
(defun signs-check (name ok) (if (not ok) (setq *sign-test-fail* (1+ *sign-test-fail*))) (princ (strcat "\n" (if ok "PASS " "FAIL ") "SIGN " name)))
(signs-check "chunks-reject-invalid-size" (and (null (bht:chunks "abc" 0)) (null (bht:chunks "abc" -1)) (equal (bht:chunks "abc" 2) (quote ("ab" "c")))))
(signs-check "removed-command-aliases" (not (vl-some 'bht:fn-defined-p '(c:BHTIMPORT c:BHTCSV c:BHTNK c:BHTLABEL c:BHTTAG c:BHTEDIT c:BHTDELETE c:BHTUNTAG c:BHTDSANH c:BHTSYNCANH c:BHTPHOTO c:BHTEXPORT c:BHTSUMMARY c:BHTCHECK))))
(signs-check "invalid-speed-validation" (/= (BHTSIGNVALIDATE "P.127-800") ""))
(signs-check "native-family-rejects-extra-suffix" (and (bht:bb-family-p "W207A" "W207") (not (bht:bb-family-p "W207ZZ" "W207"))))
(signs-check "invalid-cached-vector-not-reused" (= (bht:bb-block-for "W.207zz") "BHT_KH_BIEN_BAO_V044"))
(setq pl (entmakex '((0 . "LWPOLYLINE") (100 . "AcDbEntity") (8 . "0") (100 . "AcDbPolyline") (90 . 2) (70 . 0) (10 0.0 0.0) (10 100.0 0.0))))
(bht:route-create "SIGNROUTE" pl "TIM_DUONG" 20.0 0.0 nil "test")
(bht:route-set-start-dir "SIGNROUTE" '(0.0 0.0 0.0) 1)
(setq rec (list (cons "nhom" "BIEN_BAO") (cons "route_id" "SIGNROUTE") (cons "phia_tuyen" "PHAI")))
(setq result (bht:kh-auto-transform rec '(50.0 -5.0 0.0) 1.0))
(signs-check "right-forward-90" (equal (cadr result) (/ pi 2.0) 1e-8))
(setq rec (bht:set rec "phia_tuyen" "TRAI"))
(signs-check "left-forward-minus90" (equal (cadr (bht:kh-auto-transform rec '(50.0 5.0 0.0) 1.0)) (- (/ pi 2.0)) 1e-8))
(bht:route-set-start-dir "SIGNROUTE" '(100.0 0.0 0.0) -1)
(setq result (bht:kh-auto-transform rec '(50.0 -5.0 0.0) 1.0))
(signs-check "reverse-left" (equal (sin (cadr result)) 1.0 1e-8))
(setq rec (bht:set rec "nhom" "COC_TIEU"))
(setq result (bht:kh-auto-transform rec '(50.0 -5.0 0.0) 1.0))
(signs-check "post-stays-at-survey" (equal (car result) '(50.0 -5.0 0.0) 1e-8))
(signs-check "post-rotates" (equal (abs (sin (cadr result))) 1.0 1e-8))
(setq rec (bht:set rec "route_id" ""))
(signs-check "no-route-zero" (equal (cadr (bht:kh-auto-transform rec '(50.0 -5.0 0.0) 1.0)) 0.0 1e-8))
(bht:block "SIGN_CUSTOM_TEST" (list (bht:line-g '(0.0 0.0 0.0) '(1.0 1.0 0.0))))
(setq rec (bht:set rec "custom_block" "SIGN_CUSTOM_TEST"))
(signs-check "object-custom-priority" (= (bht:kh-block rec) "SIGN_CUSTOM_TEST"))
(setq rec (list (cons "nhom" "BIEN_BAO") (cons "ma_hieu" "P.127") (cons "mo_ta" "gioihan80")))
(signs-check "cache-name-matches-current-geometry" (= (bht:tdt-block-name "P.127-80") "BHT_TDT_V0613_P_127_80"))
(setq sign-expected-speed80 (cond ((= (getenv "BHT_SIGN_PROVIDER") "BUILTIN") "BHT_KH_BB_P127_80_NATIVE") ((= (getenv "BHT_TEST_ADS") "1") "BHT_SIGN_V0633_P_127_80") (T "BHT_TDT_V0613_P_127_80")))
(signs-check "description-import-80" (= (bht:kh-block rec) sign-expected-speed80))
(signs-check "nonuniform-global-custom-factor-ignored" (progn (bht:meta-set "kh_block_bien_bao" "SIGN_CUSTOM_TEST") (bht:meta-set "kh_block_factor_bien_bao" "3") (setq rec (bht:set rec "custom_block" "SIGN_CUSTOM_TEST")) (equal (bht:kh-scale-for rec) (bht:kh-scale) 1e-8)))
(bht:meta-set "kh_block_bien_bao" "")
(bht:meta-set "kh_block_factor_bien_bao" "1")
(setq survey (entmakex '((0 . "POINT") (10 50.0 -5.0 0.0))))
(bht:pt-write-xdata survey "SIGN-PT" "SIGN" "1" "Sign" -5.0 50.0 0.0 "BIEN_BAO" "test" "gioihan80" "")
(setq fields (list (cons "nhom" "BIEN_BAO") (cons "ma_hieu" "P.127") (cons "mo_ta" "gioihan80") (cons "custom_block" "SIGN_CUSTOM_TEST")))
(setq new (bht:obj-create "OBJ-SIGN" fields '("SIGN-PT") nil))
(signs-check "lisp-create-custom" (and (car new) (= (bht:get (bht:obj-read "OBJ-SIGN") "custom_block") "SIGN_CUSTOM_TEST")))
(setq rec (bht:obj-read "OBJ-SIGN"))
(setq rec (bht:set (bht:set (bht:set rec "custom_block" "") "route_id" "SIGNROUTE") "phia_tuyen" "TRAI"))
(bht:obj-write "OBJ-SIGN" rec)
(setq sync1 (bht:symbol-sync '("OBJ-SIGN")))
(setq sym (cadr (assoc "OBJ-SIGN" (bht:group-pairs (bht:tagged-pairs "INSERT" "BHT_KH" 1)))))
(signs-check "sync-creates-speed80" (and sym (= (cdr (assoc 2 (entget sym))) sign-expected-speed80)))
(setq before (entget sym) sync2 (bht:symbol-sync '("OBJ-SIGN")))
(signs-check "repeat-sync-idempotent" (and (= (cdr (assoc 'created sync2)) 0) (equal before (entget sym))))
(entmod (bht:dxf-put (entget sym) 50 0.321))
(bht:symbol-sync '("OBJ-SIGN"))
(signs-check "manual-rotation-preserved" (equal (cdr (assoc 50 (entget sym))) 0.321 1e-8))
;; Free placement persists independently from route, and leads via picked corners.
(setq source-record (bht:obj-read "OBJ-SIGN") source-point (entget survey))
(bht:kh-free-apply "OBJ-SIGN" '(65.0 -25.0 0.0) 0.75 '((55.0 -8.0 0.0) (60.0 -18.0 0.0)))
(setq free-record (bht:obj-read "OBJ-SIGN") free-leader (cadr (assoc "OBJ-SIGN" (bht:group-pairs (bht:tagged-pairs "LWPOLYLINE" "BHT_KH" 1)))))
(signs-check "free-position-angle" (and (equal (cdr (assoc 10 (entget sym))) '(65.0 -25.0 0.0) 1e-8) (equal (cdr (assoc 50 (entget sym))) 0.75 1e-8)))
(signs-check "free-route-and-RTK-kept" (and (= (bht:get source-record "route_id") (bht:get free-record "route_id")) (equal source-point (entget survey))))
(signs-check "free-polyline-four-vertices" (and free-leader (= (cdr (assoc 90 (entget free-leader))) 4)
  (equal (mapcar 'cdr (vl-remove-if-not '(lambda (pair) (= (car pair) 10)) (entget free-leader))) '((50.0 -5.0) (55.0 -8.0) (60.0 -18.0) (65.0 -25.0)) 1e-8)))
(setq free-before (entget free-leader) ins-before (entget sym))
(bht:symbol-sync '("OBJ-SIGN"))
(signs-check "free-repeat-idempotent" (and (equal free-before (entget free-leader)) (equal ins-before (entget sym))))
(entmod (bht:dxf-put (entget sym) 10 '(70.0 -30.0 0.0)))
(bht:symbol-sync '("OBJ-SIGN"))
(signs-check "free-move-updates-end-keeps-corners" (equal (mapcar 'cdr (vl-remove-if-not '(lambda (pair) (= (car pair) 10)) (entget free-leader))) '((50.0 -5.0) (55.0 -8.0) (60.0 -18.0) (70.0 -30.0)) 1e-8))
(bht:kh-free-apply "OBJ-SIGN" '(80.0 -20.0 0.0) 1.25 nil)
(signs-check "free-replace-route-straight" (and (= (length (bht:tagged-pairs "LWPOLYLINE" "BHT_KH" 1)) 0) (= (length (vl-remove-if-not '(lambda (pair) (= (car pair) "OBJ-SIGN")) (bht:tagged-pairs "LINE" "BHT_KH" 1))) 1)
  (equal (cdr (assoc 10 (entget sym))) '(80.0 -20.0 0.0) 1e-8)))
(bht:kh-free-apply "OBJ-SIGN" '(65.0 -25.0 0.0) 0.75 '((60.0 -18.0 0.0)))
(bht:symbol-reset '("OBJ-SIGN"))
(signs-check "free-reset-to-route" (and (= (bht:get (bht:obj-read "OBJ-SIGN") "kh_mode") "")
 (= (length (bht:tagged-pairs "LWPOLYLINE" "BHT_KH" 1)) 0)
 (equal (cdr (assoc 10 (entget sym))) (car (bht:kh-route-transform (bht:obj-read "OBJ-SIGN") '(50.0 -5.0 0.0) (bht:kh-scale))) 1e-8)))
(setq before-missing-ids (bht:obj-ids) before-missing-sym (entget sym))
(signs-check "missing-free-object-returns-error" (eq (car (bht:kh-place-free "__MISSING__")) 'LOI))
(signs-check "missing-free-object-API-error" (= (car (bht:api-sign-free "__MISSING__")) "LOI"))
(signs-check "empty-free-object-returns-error" (eq (car (bht:kh-place-free nil)) 'LOI))
(signs-check "missing-object-does-not-write" (and (equal before-missing-ids (bht:obj-ids)) (equal before-missing-sym (entget sym))))
(bht:kh-free-apply "OBJ-SIGN" '(65.0 -25.0 0.0) 0.75 '((55.0 -8.0 0.0) (60.0 -18.0 0.0)))
(setq leader-order (cadr (assoc "OBJ-SIGN" (bht:group-pairs (bht:tagged-pairs "LWPOLYLINE" "BHT_KH" 1)))))
(bht:kh-free-apply "OBJ-SIGN" '(65.0 -25.0 0.0) 0.75 '((60.0 -18.0 0.0) (55.0 -8.0 0.0)))
(signs-check "changed-waypoint-order-kept" (equal (bht:kh-leader-xy (bht:kh-via-points (bht:obj-read "OBJ-SIGN"))) '((60.0 -18.0) (55.0 -8.0))))
(signs-check "changed-waypoint-order-on-entity" (equal (mapcar 'cdr (vl-remove-if-not '(lambda (pair) (= (car pair) 10)) (entget leader-order))) '((50.0 -5.0) (60.0 -18.0) (55.0 -8.0) (65.0 -25.0)) 1e-8))
(setq leader-before (entget leader-order))
(bht:symbol-sync '("OBJ-SIGN"))
(signs-check "reordered-leader-repeat-idempotent" (equal leader-before (entget leader-order)))
(bht:obj-write "OBJ-NOPOINT" '(("nhom" . "BIEN_BAO")))
(signs-check "free-no-RTK-returns-error" (eq (car (bht:kh-place-free "OBJ-NOPOINT")) 'LOI))
(bht:obj-delete "OBJ-NOPOINT")
(bht:symbol-reset '("OBJ-SIGN"))
(princ (strcat "\nSIGN-TEST-FAIL=" (itoa *sign-test-fail*)))
(princ)
(foreach board-group '("BANG_QC" "KHAC" "CHUA_XAC_DINH")
  (setq board-id (strcat "OBJ-BOARD-" board-group)
        board-fields (list (cons "nhom" board-group) (cons "mo_ta" "Cửa hàng vật liệu")))
  (bht:obj-create board-id board-fields '("SIGN-PT") T)
  (bht:kh-free-apply board-id '(32.0 12.0 0.0) 0.35 nil)
  (setq board-rec (bht:obj-read board-id)
        board-ins (cdr (assoc board-id (bht:tagged-pairs "INSERT" "BHT_KH" 1)))
        board-name (cdr (assoc 2 (entget board-ins))))
  (signs-check (strcat "named-board-" board-group)
    (and (wcmatch board-name "BHT_BOARD_V0625_*") (= (bht:kh-label board-id board-rec) "")
         (null (assoc board-id (bht:tagged-pairs "TEXT" "BHT_KH" 1)))))
  (if (= board-group "CHUA_XAC_DINH")
    (signs-check "unknown-board-fixed-title" (= board-name (BHTNAMEDBOARD "Chưa xác định" (bht:kh-label-style "Chưa xác định")))))
  (setq board-before (entget board-ins))
  (bht:symbol-sync (list board-id))
  (signs-check (strcat "board-idempotent-" board-group) (equal board-before (entget board-ins)))
  (bht:obj-write board-id (bht:set board-rec "mo_ta" "Tên mới"))
  (bht:symbol-sync (list board-id))
  (signs-check (strcat "board-edit-keeps-position-" board-group)
    (and (equal (cdr (assoc 10 (entget board-ins))) '(32.0 12.0 0.0) 1e-6)
         (equal (cdr (assoc 50 (entget board-ins))) 0.35 1e-6)
         (if (= board-group "CHUA_XAC_DINH") (= board-name (cdr (assoc 2 (entget board-ins))))
           (/= board-name (cdr (assoc 2 (entget board-ins)))))))
  (bht:obj-write board-id (bht:set board-rec "custom_block" "SIGN_CUSTOM_TEST"))
  (signs-check (strcat "board-custom-block-priority-" board-group) (= (bht:kh-block (bht:obj-read board-id)) "SIGN_CUSTOM_TEST")))

(if (= (getenv "BHT_SIGN_PROVIDER") "BUILTIN")
  (progn
    (setq block80 (bht:kh-block '(("nhom" . "BIEN_BAO") ("ma_hieu" . "P.127") ("mo_ta" . "gioihan80"))))
    (setq ent80 (tblobjname "BLOCK" block80) found80 nil)
    (while (and (setq ent80 (entnext ent80)) (/= (cdr (assoc 0 (entget ent80))) "ENDBLK"))
      (if (and (= (cdr (assoc 0 (entget ent80))) "TEXT") (= (cdr (assoc 1 (entget ent80))) "80")) (setq found80 T)))
    (signs-check "offline-speed-80-visible-text" found80)
    (signs-check "offline-120-not-confused-with20" (= (bht:bb-block-for "P.127-120") "BHT_KH_BB_P127_120_NATIVE"))))
(princ (strcat "\nSIGN-TEST-FAIL=" (itoa *sign-test-fail*)))

(setq filled-name (cdr (assoc 2 (entget sym))) fillmode-before (getvar "FILLMODE")
      placement-before (list (cdr (assoc 10 (entget sym))) (cdr (assoc 50 (entget sym))) (cdr (assoc 41 (entget sym)))))
(bht:meta-set "sign_fill_all" "0")
(bht:symbol-sync '("OBJ-SIGN"))
(setq unfilled-name (cdr (assoc 2 (entget sym))))
(signs-check "fill-off-variant" (and (/= unfilled-name filled-name) (wcmatch unfilled-name "*_NOFILL_V0633")))
(signs-check "fill-switch-keeps-placement" (equal placement-before (list (cdr (assoc 10 (entget sym))) (cdr (assoc 50 (entget sym))) (cdr (assoc 41 (entget sym))))))
(setq outline-before (entget sym))
(bht:symbol-sync '("OBJ-SIGN"))
(signs-check "fill-off-sync-idempotent" (equal outline-before (entget sym)))
(bht:meta-set "sign_fill_all" "1")
(bht:symbol-sync '("OBJ-SIGN"))
(signs-check "fill-on-restores-original" (= filled-name (cdr (assoc 2 (entget sym)))))
(signs-check "fillmode-global-unchanged" (= fillmode-before (getvar "FILLMODE")))
(setq builtin-source (bht:bb-block-for "P.127-80"))
(bht:meta-set "sign_fill_all" "0")
(signs-check "custom-block-outline-isolated" (/= builtin-source (bht:kh-block (list '("nhom" . "BIEN_BAO") '("sign_fill" . "0") (cons "custom_block" builtin-source)))))
(princ (strcat "\nSIGN-TEST-FAIL=" (itoa *sign-test-fail*)))

(bht:meta-set "sign_fill_all" "1")
(signs-check "symbol-layer-white" (= (cdr (assoc 62 (tblsearch "LAYER" "BHT_KYHIEU"))) 7))
(signs-check "compact-default-label-height" (equal (bht:kh-h) 0.35 1e-6))
(signs-check "custom-label-height" (equal (bht:kh-label-height '(("kh_label_h" . "0.25"))) (* 0.36 (bht:kh-scale)) 1e-6))
(signs-check "quick-invalid-mode-error" (= (car (bht:api-sign-place "OBJ-SIGN" "BAD" "HORIZONTAL" "0")) "LOI"))
(princ (strcat "\nSIGN-TEST-FAIL=" (itoa *sign-test-fail*)))

(bht:obj-write "OBJ-SIGN" (bht:set (bht:obj-read "OBJ-SIGN") "kh_label_h" "0.25"))
(bht:symbol-sync '("OBJ-SIGN"))
(setq compact-label (cadr (assoc "OBJ-SIGN" (bht:group-pairs (bht:tagged-pairs "TEXT" "BHT_KH" 1)))))
(signs-check "label-height-on-CAD-entity" (and compact-label (and (= (cdr (assoc 72 (entget compact-label))) 1) (= (cdr (assoc 73 (entget compact-label))) 3))))
(princ (strcat "\nSIGN-TEST-FAIL=" (itoa *sign-test-fail*)))

(setq unrelated (entmakex '((0 . "SOLID") (8 . "0") (10 0.0 0.0 0.0) (11 1.0 0.0 0.0) (12 0.0 1.0 0.0) (13 1.0 1.0 0.0))) unrelated-before (entget unrelated))
(bht:obj-write "OBJ-SECOND" (bht:set (bht:obj-read "OBJ-SIGN") "sign_fill" "1"))
(bht:obj-write "OBJ-UNSEEN" (bht:obj-read "OBJ-SIGN"))
(bht:symbol-sync '("OBJ-SECOND"))
(signs-check "global-fill-API-off" (= (car (bht:api-sign-fill "0")) "OK"))
(setq fill-pairs (bht:tagged-pairs "INSERT" "BHT_KH" 1))
(signs-check "global-fill-all-existing-signs" (and (wcmatch (cdr (assoc 2 (entget (cdr (assoc "OBJ-SIGN" fill-pairs))))) "*_NOFILL_V0633") (wcmatch (cdr (assoc 2 (entget (cdr (assoc "OBJ-SECOND" fill-pairs))))) "*_NOFILL_V0633")))
(signs-check "global-fill-does-not-insert-unseen" (null (assoc "OBJ-UNSEEN" fill-pairs)))
(signs-check "global-fill-keeps-unrelated-geometry" (equal unrelated-before (entget unrelated)))
(signs-check "global-fill-policy-persisted" (= (bht:meta "sign_fill_all" "1") "0"))
(signs-check "global-fill-API-on" (= (car (bht:api-sign-fill "1")) "OK"))
(bht:kh-free-apply "OBJ-SIGN" '(65.0 -25.0 0.0) 2.4 '((60.0 -18.0 0.0)))
(setq compact-label (cdr (assoc "OBJ-SIGN" (bht:tagged-pairs "TEXT" "BHT_KH" 1))) label-data (entget compact-label)
      sign-data (entget (cdr (assoc "OBJ-SIGN" (bht:tagged-pairs "INSERT" "BHT_KH" 1)))))
(setq wanted-layout (bht:kh-sign-label-layout (cdr (assoc 2 sign-data)) (list (cdr (assoc 10 sign-data)) (cdr (assoc 41 sign-data)) (cdr (assoc 50 sign-data)))))
(signs-check "label-exact-sign-rotation-with-waypoints" (equal (cdr (assoc 50 label-data)) 2.4 1e-6))
(signs-check "label-bottom-center-alignment" (and (= (cdr (assoc 72 label-data)) 1) (= (cdr (assoc 73 label-data)) 3) (equal (cdr (assoc 11 label-data)) (car wanted-layout) 1e-6)))
(signs-check "label-height-follows-sign" (equal (cdr (assoc 40 label-data)) (cadr wanted-layout) 1e-6))
(bht:obj-delete "OBJ-SECOND") (bht:obj-delete "OBJ-UNSEEN")
(princ (strcat "\nSIGN-TEST-FAIL=" (itoa *sign-test-fail*)))
(signs-check "no-legacy-upgrade-commands" (and (not (bht:fn-defined-p 'c:BHTNANGCAP)) (not (bht:fn-defined-p 'c:BHTVEMODEL)) (not (bht:fn-defined-p 'c:BHTROUTE))))
(signs-check "metre-label-readable" (= (bht:kh-code-label "BIEN_BAO" "S.509a@4.5") "S.509a (4.5 m)"))
(bht:obj-create "OBJ-POST" '(("nhom" . "COC_TIEU")) '("SIGN-PT") T)
(bht:obj-write "OBJ-POST" (bht:set (bht:obj-read "OBJ-POST") "ly_trinh_km" "Km1+200.00"))
(bht:kh-free-apply "OBJ-POST" '(20.0 30.0 0.0) 0.7 nil)
(setq post (cdr (assoc "OBJ-POST" (bht:tagged-pairs "INSERT" "BHT_KH" 1))) post-label (cdr (assoc "OBJ-POST" (bht:tagged-pairs "TEXT" "BHT_KH" 1))))
(setq post-source (bht:obj-position (bht:obj-read "OBJ-POST") (bht:pt-all)))
(signs-check "delineator-tail-at-survey-point" (and post (= (cdr (assoc 2 (entget post))) "BHT_KH_COC_TIEU")
  (equal (cdr (assoc 10 (entget post))) post-source 1e-6)
  (null (assoc "OBJ-POST" (bht:tagged-pairs "LWPOLYLINE" "BHT_KH" 1)))))
(setq s (cdr (assoc 41 (entget post))) post-label-vector (mapcar '- (cdr (assoc 11 (entget post-label))) post-source))
(signs-check "delineator-label-below-symbol-and-rotates" (and post-label
  (< (+ (* (- (sin 0.7)) (car post-label-vector)) (* (cos 0.7) (cadr post-label-vector))) (* -0.34 s))
  (equal (cdr (assoc 50 (entget post-label))) 0.7 1e-6)))
(setq before-post (entget post) before-post-label (entget post-label))
(bht:symbol-sync '("OBJ-POST"))
(signs-check "delineator-sync-idempotent" (and (equal before-post (entget post)) (equal before-post-label (entget post-label))))
(bht:obj-create "OBJ-OTHER" '(("nhom" . "CONG_TRINH")) '("SIGN-PT") T)
(bht:kh-free-apply "OBJ-OTHER" '(25.0 30.0 0.0) 1.2 '((15.0 20.0 0.0)))
(setq other (cdr (assoc "OBJ-OTHER" (bht:tagged-pairs "INSERT" "BHT_KH" 1))))
(signs-check "other-group-free-placement-and-direction" (and other (equal (cdr (assoc 10 (entget other))) '(25.0 30.0 0.0) 1e-6) (equal (cdr (assoc 50 (entget other))) 1.2 1e-6)))
(signs-check "assembly-function-registered-for-lisp" (bht:fn-defined-p 'BHTSIGNASSEMBLY))
(bht:obj-create "OBJ-MULTI" '(("nhom" . "BIEN_BAO") ("ma_hieu" . "W.239") ("so_tru" . "1") ("so_mat" . "2") ("mat" . "W.239") ("mat" . "S.509a@7")) '("SIGN-PT") T)
(setq multi-reply (bht:api-symbol-sync "OBJ-MULTI"))
(signs-check "api-two-plates-seven-metres-success" (= (car multi-reply) "OK"))
(setq multi-insert (cdr (assoc "OBJ-MULTI" (bht:tagged-pairs "INSERT" "BHT_KH" 1))) plate-count 0)
(if multi-insert
 (progn
  (setq multi-name (cdr (assoc 2 (entget multi-insert))) multi-entity (tblobjname "BLOCK" multi-name))
  (while (and (setq multi-entity (entnext multi-entity)) (/= (cdr (assoc 0 (entget multi-entity))) "ENDBLK"))
   (if (= (cdr (assoc 0 (entget multi-entity))) "INSERT") (setq plate-count (1+ plate-count))))))
(signs-check "api-one-post-two-visible-plates" (and multi-insert (= plate-count 2)))
(setq multi-before (entget multi-insert))
(bht:api-symbol-sync "OBJ-MULTI")
(signs-check "api-two-plates-update-idempotent" (equal multi-before (entget multi-insert)))
(princ (strcat "\nSIGN-TEST-FAIL=" (itoa *sign-test-fail*)))
(if (= (getenv "BHT_SIGN_PROVIDER") "BUILTIN")
 (foreach code '("S.501@350" "S.502@150" "S.509a@4.5" "P.119@8")
  (setq block-m (bht:bb-block-for code) e-m (tblobjname "BLOCK" block-m) found-m nil)
  (while (and (setq e-m (entnext e-m)) (/= (cdr (assoc 0 (entget e-m))) "ENDBLK"))
   (if (and (= (cdr (assoc 0 (entget e-m))) "TEXT") (= (cdr (assoc 1 (entget e-m))) (BHTMETRETEXT code "10 m"))) (setq found-m T)))
  (signs-check (strcat "offline-metres-" code) found-m)))
(signs-check "truck-weight-label-unit" (= (bht:kh-code-label "BIEN_BAO" "S.505a@8") "S.505a (8T)"))
(if (/= (getenv "BHT_SIGN_PROVIDER") "BUILTIN")
 (progn
  (bht:obj-create "OBJ-WEIGHT" '(("nhom" . "BIEN_BAO") ("ma_hieu" . "P.124a") ("so_tru" . "1") ("so_mat" . "2") ("mat" . "P.124a") ("mat" . "S.505a@8")) '("SIGN-PT") T)
  (signs-check "truck-weight-record-sync" (= (car (bht:api-symbol-sync "OBJ-WEIGHT")) "OK"))
  (signs-check "truck-weight-face-saved" (member "S.505a@8" (mapcar 'cdr (vl-remove-if-not '(lambda (pair) (= (car pair) "mat")) (bht:obj-read "OBJ-WEIGHT")))))))
(setq multi-labels (cdr (assoc "OBJ-MULTI" (bht:group-pairs (bht:tagged-pairs "TEXT" "BHT_KH" 1)))))
(signs-check "two-plates-have-two-labels" (= (length multi-labels) 2))
(signs-check "supplementary-label-includes-code-and-value" (vl-some '(lambda (e) (= (cdr (assoc 1 (entget e))) "S.509a (7 m)")) multi-labels))
(setq multi-labels-before (mapcar 'entget multi-labels))
(bht:api-symbol-sync "OBJ-MULTI")
(signs-check "two-face-labels-update-idempotent" (equal multi-labels-before (mapcar 'entget multi-labels)))
(bht:obj-create "OBJ-REPEAT" '(("nhom" . "BIEN_BAO") ("ma_hieu" . "P.127-80") ("so_mat" . "2") ("mat" . "P.127-80") ("mat" . "P.127-80")) '("SIGN-PT") T)
(bht:api-symbol-sync "OBJ-REPEAT")
(setq repeat-labels (cdr (assoc "OBJ-REPEAT" (bht:group-pairs (bht:tagged-pairs "TEXT" "BHT_KH" 1)))))
(signs-check "repeated-face-labels-not-collapsed" (= (length repeat-labels) 2))
(bht:obj-write "OBJ-MULTI" (bht:set (vl-remove-if '(lambda (pair) (= (car pair) "mat")) (bht:obj-read "OBJ-MULTI")) "so_mat" "1"))
(bht:api-symbol-sync "OBJ-MULTI")
(signs-check "removed-plate-removes-extra-label" (= (length (cdr (assoc "OBJ-MULTI" (bht:group-pairs (bht:tagged-pairs "TEXT" "BHT_KH" 1))))) 1))
(bht:obj-write "OBJ-SCALE-UNSEEN" (bht:obj-read "OBJ-SIGN"))
(setq scale-point-before (bht:pt-all) scale-record-before (bht:obj-read "OBJ-SIGN")
      scale-other-before (entget other) scale-post-before (entget post) scale-post-label-before (entget post-label)
      scale-label (car repeat-labels) scale-label-h (cdr (assoc 40 (entget scale-label)))
      scale-auto (cdr (assoc "OBJ-REPEAT" (bht:tagged-pairs "INSERT" "BHT_KH" 1))))
(setq scale-d (entget sym))
(entmod (bht:dxf-put (bht:dxf-put scale-d 10 '(70.0 -27.0 0.0)) 50 1.3))
(setq scale-manual-position (cdr (assoc 10 (entget sym))) scale-auto-position (cdr (assoc 10 (entget scale-auto))))
(signs-check "scale-api-separate-symbol-label" (= (car (bht:api-sign-scale "2" "0,75")) "OK"))
(signs-check "scale-manual-sign-keeps-location-angle" (and (equal scale-manual-position (cdr (assoc 10 (entget sym)))) (equal (cdr (assoc 50 (entget sym))) 1.3 1e-8) (equal (cdr (assoc 41 (entget sym))) 2.0 1e-8)))
(signs-check "scale-auto-sign-keeps-location" (and (equal scale-auto-position (cdr (assoc 10 (entget scale-auto)))) (equal (cdr (assoc 41 (entget scale-auto))) 2.0 1e-8)))
(signs-check "scale-label-independent-of-symbol" (equal (cdr (assoc 40 (entget scale-label))) (* 0.75 scale-label-h) 1e-8))
(signs-check "scale-all-face-labels" (and (= (length repeat-labels) 2) (vl-every '(lambda (e) (equal (cdr (assoc 40 (entget e))) (* 0.75 scale-label-h) 1e-8)) repeat-labels)))
(signs-check "scale-keeps-RTK-records-and-other-groups" (and (equal scale-point-before (bht:pt-all)) (equal scale-record-before (bht:obj-read "OBJ-SIGN")) (equal scale-other-before (entget other)) (equal scale-post-before (entget post)) (equal scale-post-label-before (entget post-label)) (equal unrelated-before (entget unrelated))))
(signs-check "scale-does-not-create-missing-sign" (null (assoc "OBJ-SCALE-UNSEEN" (bht:tagged-pairs "INSERT" "BHT_KH" 1))))
(setq scale-before (entget sym) scale-auto-before (entget scale-auto) scale-labels-before (mapcar 'entget repeat-labels))
(bht:api-sign-scale "2" "0.75")
(signs-check "scale-repeated-apply-idempotent" (and (equal scale-before (entget sym)) (equal scale-auto-before (entget scale-auto)) (equal scale-labels-before (mapcar 'entget repeat-labels))))
(bht:symbol-sync nil)
(signs-check "scale-survives-later-sync" (and (equal scale-manual-position (cdr (assoc 10 (entget sym)))) (equal scale-auto-position (cdr (assoc 10 (entget scale-auto)))) (equal (cdr (assoc 41 (entget sym))) 2.0 1e-8)))
(signs-check "scale-new-sign-uses-drawing-setting" (equal (cdr (assoc 41 (entget (cdr (assoc "OBJ-SCALE-UNSEEN" (bht:tagged-pairs "INSERT" "BHT_KH" 1)))))) 2.0 1e-8))
(setq scale-before (entget sym))
(bht:api-sign-scale "2" "1.5")
(signs-check "scale-label-only-keeps-symbol" (and (equal scale-before (entget sym)) (equal (cdr (assoc 40 (entget scale-label))) (* 1.5 scale-label-h) 1e-8)))
(setq scale-before (entget sym) scale-label-before (entget scale-label))
(foreach invalid '("0" "-1" "101" "0.001" "abc" "1.0001" "")
  (signs-check (strcat "scale-invalid-symbol-" invalid) (= (car (bht:api-sign-scale invalid "1")) "LOI"))
  (signs-check (strcat "scale-invalid-label-" invalid) (= (car (bht:api-sign-scale "1" invalid)) "LOI")))
(signs-check "scale-invalid-input-does-not-mutate" (and (= (bht:meta "sign_scale" "") "2.000") (= (bht:meta "sign_label_scale" "") "1.500") (equal scale-before (entget sym)) (equal scale-label-before (entget scale-label))))
(signs-check "scale-reset-standard" (= (car (bht:api-sign-scale "1" "1")) "OK"))
(bht:api-label-sync "ALL")
(setq rtk-labels (mapcar 'cdr (bht:tagged-pairs "TEXT" "BHT_NHAN" 2))
      rtk-manual (car rtk-labels) rtk-manual-pos '(120.0 80.0 0.0))
(entmod (bht:dxf-put (entget rtk-manual) 10 rtk-manual-pos))
(setq rtk-before (bht:pt-all) rtk-entity-before (entget survey '("BHT_PT"))
      rtk-labels-before (mapcar '(lambda (e) (entget e '("BHT_NHAN"))) rtk-labels)
      rtk-symbol-before (entget sym) rtk-code-before (entget scale-label))
(signs-check "RTK-scale-independent-values" (= (car (bht:api-rtk-scale "2" "1,5")) "OK"))
(signs-check "RTK-scale-X-display-and-persisted-height" (and (= (getvar "PDMODE") 3) (equal (getvar "PDSIZE") 2.0 1e-9) (= (bht:meta "pt_size" "") "2.000") (equal (bht:num (bht:meta "nhan_h" "")) 0.75 1e-9)))
(signs-check "RTK-scale-all-existing-labels" (and rtk-labels (vl-every '(lambda (e) (equal (cdr (assoc 40 (entget e))) 0.75 1e-9)) rtk-labels)))
(signs-check "RTK-scale-preserves-label-location-content-xdata" (equal (mapcar '(lambda (d) (vl-remove-if '(lambda (v) (= (car v) 40)) d)) rtk-labels-before) (mapcar '(lambda (e) (vl-remove-if '(lambda (v) (= (car v) 40)) (entget e '("BHT_NHAN")))) rtk-labels)))
(signs-check "RTK-scale-preserves-survey-and-signs" (and (equal rtk-before (bht:pt-all)) (equal rtk-entity-before (entget survey '("BHT_PT"))) (equal rtk-symbol-before (entget sym)) (equal rtk-code-before (entget scale-label))))
(setq rtk-after (mapcar 'entget rtk-labels))
(bht:api-rtk-scale "2" "1.5")
(signs-check "RTK-scale-repeat-idempotent" (equal rtk-after (mapcar 'entget rtk-labels)))
(foreach invalid '("0" "-1" "101" "0.001" "abc" "1.0001" "")
  (signs-check (strcat "RTK-scale-invalid-X-" invalid) (= (car (bht:api-rtk-scale invalid "1")) "LOI"))
  (signs-check (strcat "RTK-scale-invalid-label-" invalid) (= (car (bht:api-rtk-scale "1" invalid)) "LOI")))
(signs-check "RTK-scale-invalid-atomic" (and (equal rtk-after (mapcar 'entget rtk-labels)) (equal (getvar "PDSIZE") 2.0 1e-9) (equal (bht:num (bht:meta "nhan_h" "")) 0.75 1e-9)))
(setq rtk-new (entmakex '((0 . "POINT") (10 150.0 60.0 0.0))))
(bht:pt-write-xdata rtk-new "RTK-SCALE-NEW" "SIGN" "2" "New" 60.0 150.0 0.0 "CHUA_XAC_DINH" "test" "scale" "")
(bht:api-rtk-scale "0,5" "0.015")
(signs-check "RTK-scale-keeps-half-step-precision" (equal (bht:num (bht:meta "nhan_h" "")) 0.0075 1e-10))
(signs-check "RTK-scale-does-not-create-missing-labels" (not (vl-some '(lambda (pair) (wcmatch (car pair) "RTK-SCALE-NEW|*")) (bht:tagged-pairs "TEXT" "BHT_NHAN" 2))))
(signs-check "RTK-label-update-separate-API" (= (car (bht:api-label-sync "ALL")) "OK"))
(signs-check "RTK-label-update-keeps-X-and-manual-location" (and (equal (getvar "PDSIZE") 0.5 1e-9) (equal (cdr (assoc 10 (entget rtk-manual))) rtk-manual-pos 1e-9)))
(setq rtk-new-labels (vl-remove-if-not '(lambda (pair) (wcmatch (car pair) "RTK-SCALE-NEW|*")) (bht:tagged-pairs "TEXT" "BHT_NHAN" 2)))
(signs-check "RTK-new-labels-use-saved-scale" (and rtk-new-labels (vl-every '(lambda (pair) (equal (cdr (assoc 40 (entget (cdr pair)))) 0.0075 1e-10)) rtk-new-labels)))
(signs-check "RTK-label-update-keeps-original-survey" (equal rtk-entity-before (entget survey '("BHT_PT"))))
(bht:api-rtk-scale "1" "1")
(signs-check "RTK-scale-reset-standard" (and (equal (getvar "PDSIZE") 1.0 1e-9) (equal (bht:num (bht:meta "nhan_h" "")) 0.5 1e-9)))
(princ (strcat "\nSIGN-TEST-FAIL=" (itoa *sign-test-fail*)))

(bht:obj-create "OBJ-LIGHT" '(("nhom" . "DEN")) '("SIGN-PT") T)
(bht:kh-free-apply "OBJ-LIGHT" '(180.0 30.0 0.0) 0.7 nil)
(setq light-insert (cdr (assoc "OBJ-LIGHT" (bht:tagged-pairs "INSERT" "BHT_KH" 1))) light-label (cdr (assoc "OBJ-LIGHT" (bht:tagged-pairs "TEXT" "BHT_KH" 1))))
(signs-check "traffic-light-has-no-label" (null light-label))
(setq light-before (entget light-insert) light-survey-before (bht:pt-all))
(bht:api-symbol-sync "OBJ-LIGHT")
(signs-check "traffic-light-sync-stable-and-keeps-RTK" (and (equal light-before (entget light-insert)) (equal light-survey-before (bht:pt-all)) (null (assoc "OBJ-LIGHT" (bht:tagged-pairs "TEXT" "BHT_KH" 1)))))
(bht:obj-create "OBJ-TOLL" '(("nhom" . "BIEN_BAO") ("ma_hieu" . "IE.472a@500")) '("SIGN-PT") T)
(signs-check "toll-native-sign-sync" (= (car (bht:api-symbol-sync "OBJ-TOLL")) "OK"))
(setq toll-label (cdr (assoc "OBJ-TOLL" (bht:tagged-pairs "TEXT" "BHT_KH" 1))))
(signs-check "toll-label-includes-entered-metres" (and toll-label (= (cdr (assoc 1 (entget toll-label))) "IE.472a (500 m)")))
(princ (strcat "\nSIGN-TEST-FAIL=" (itoa *sign-test-fail*)))
