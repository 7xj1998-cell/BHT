(defun qa110-stable (v)
  (cond ((= (type v) 'REAL) (rtos v 2 8))
        ((and (listp v) (vl-list-length v)) (mapcar 'qa110-stable v))
        ((listp v) (cons (qa110-stable (car v)) (qa110-stable (cdr v)))) (T v)))
(defun qa110-saved-state ()
  (qa110-stable (list (bht:rec-all "OBJ") (bht:rec-all "ROUTE") (bht:rec-all "SEG") (bht:rec-all "META")
    (mapcar '(lambda (p) (list (car p) (bht:pv (cdr p) 'xyz))) (bht:pt-all))
    (mapcar '(lambda (p) (vl-remove-if '(lambda (v) (member (car v) '(-1 330 360))) (entget (cdr p) '("*"))))
      (append (bht:tagged-pairs "*" "BHT_KH" 1) (bht:tagged-pairs "*" "BHT_SIGN_ORIGIN" 1))))))
