(setq l126-fails 0)
(defun l126-check (name ok)
  (if (not ok) (setq l126-fails (1+ l126-fails)))
  (princ (strcat "\n" (if ok "PASS L126 " "FAIL L126 ") name)))
(defun l126-line (a b source / e)
  (setq e (entmakex (list '(0 . "LINE") (cons 10 a) (cons 11 b))))
  (entmod (append (entget e) (list (list -3 (list "BHT_KH" '(1000 . "LABEL-QA") '(1000 . "DAN") (cons 1000 source)))))) e)
(setq *bht-caption-rec* '(("object_id" . "LABEL-QA") ("nhom" . "BIEN_BAO") ("ma_hieu" . "W.207a") ("ly_trinh_km" . "Km50+123.45")))
(foreach mode '("PARALLEL" "PERPENDICULAR")
  (bht:meta-set "sign_label_orientation" mode)
  (foreach degrees '(0 45 90 135 180 225 270 315)
    (setq a (* pi (/ degrees 180.0)) end (polar '(0.0 0.0 0.0) a 20.0)
          line (l126-line '(0.0 0.0 0.0) end "ONE")
          *bht-caption-leaders* (list (list "LABEL-QA" line))
          layout (bht:kh-caption-leader-layout '((0.0 0.0 0.0) 0.369) '((0.0 0.0 0.0) 1.0 0.0))
          rot (caddr layout))
    (l126-check (strcat mode "-readable-" (itoa degrees)) (>= (cos rot) -1e-8))
    (l126-check (strcat mode "-leader-reference-" (itoa degrees))
      (if (= mode "PARALLEL") (< (abs (sin (- rot a))) 1e-8) (< (abs (cos (- rot a))) 1e-8)))
    (entdel line)))
(setq left (l126-line '(0.0 -3.0 0.0) '(20.0 -3.0 0.0) "LEFT")
      right (l126-line '(0.0 3.0 0.0) '(20.0 3.0 0.0) "RIGHT")
      rail (l126-line '(20.0 -3.0 0.0) '(20.0 3.0 0.0) "@BHT_RAIL")
      *bht-caption-leaders* (list (list "LABEL-QA" left right rail)))
(foreach mode '("PARALLEL" "PERPENDICULAR")
  (bht:meta-set "sign_label_orientation" mode)
  (foreach h '(0.369 1.107)
    (setq layout (bht:kh-caption-leader-layout (list '(0.0 0.0 0.0) h) '((0.0 0.0 0.0) 1.0 0.0))
          center (polar (car layout) (- (caddr layout) (/ pi 2.0)) (* 0.5 h 2.5)))
    (l126-check (strcat "two-post-upper-leader-datum-" mode "-" (rtos h 2 3)) (equal center '(10.0 3.0 0.0) 1e-8))))
(foreach e (list left right rail) (entdel e))
(setq *bht-caption-rec* nil *bht-caption-leaders* nil)
(setq before-meta (bht:rec-read "META" "CONFIG"))
(l126-check "invalid-orientation-rejected" (/= (car (bht:api-sign-display "2" "3" "BAD")) "OK"))
(l126-check "invalid-orientation-no-meta-change" (equal before-meta (bht:rec-read "META" "CONFIG")))
(l126-check "apply-parallel" (= (car (bht:api-sign-display "3" "3" "PARALLEL")) "OK"))
(setq before-record (bht:obj-read "BIEN_BAO") before-point (entget sp '("BHT_PT")))
(l126-check "apply-perpendicular" (= (car (bht:api-sign-display "3" "1" "PERPENDICULAR")) "OK"))
(l126-check "survey-and-station-preserved" (and (equal before-record (bht:obj-read "BIEN_BAO")) (equal before-point (entget sp '("BHT_PT")))))
(setq label-snapshot (mapcar '(lambda (p) (entget (cdr p) '("BHT_KH"))) (bht:tagged-pairs "TEXT" "BHT_KH" 1)))
(bht:api-sign-display "3" "1" "PERPENDICULAR")
(l126-check "repeat-display-idempotent" (equal label-snapshot (mapcar '(lambda (p) (entget (cdr p) '("BHT_KH"))) (bht:tagged-pairs "TEXT" "BHT_KH" 1))))
(setq support2 (entmakex '((0 . "POINT") (10 100.0 106.0 0.0))))
(bht:pt-write-xdata support2 "LABEL-PT2" "QA" "1" "1" 100.0 106.0 0.0 "" "" "" "")
(bht:obj-create "LABEL-TWO" '(("nhom" . "BIEN_BAO") ("ma_hieu" . "W.239a") ("so_tru" . "2") ("so_mat" . "2") ("mat" . "W.239a") ("mat" . "S.509a")) '("SCALE-PT" "LABEL-PT2") T)
(setq rec (bht:obj-read "LABEL-TWO") rec (bht:set rec "ly_trinh_km" "Km50+123.45") rec (bht:set rec "ly_trinh_m" "50123.450"))
(bht:obj-write "LABEL-TWO" rec)
(bht:symbol-sync '("LABEL-TWO"))
(setq sign (cdr (assoc "LABEL-TWO" (bht:tagged-pairs "INSERT" "BHT_KH" 1))))
(entmod (bht:dxf-put (bht:dxf-put (entget sign) 10 '(125.0 103.0 0.0)) 50 3.2))
(foreach mode '("PARALLEL" "PERPENDICULAR")
  (bht:api-sign-display "3" "3" mode)
  (setq texts (mapcar 'cdr (vl-remove-if-not '(lambda (p) (= (car p) "LABEL-TWO")) (bht:tagged-pairs "TEXT" "BHT_KH" 1)))
        title (car (vl-remove-if 'bht:kh-extra-label-p texts)) d (entget title) rot (cdr (assoc 50 d)) base (cdr (assoc 11 d)) h (cdr (assoc 40 d)))
  (l126-check (strcat "actual-stack-three-rows-" mode) (= (length texts) 3))
  (l126-check (strcat "actual-rotated-sign-readable-" mode) (>= (cos rot) -1e-8))
  (foreach e texts
    (setq d (entget e) x (bht:xget e "BHT_KH"))
    (l126-check (strcat "actual-row-angle-" mode "-" (bht:str (nth 5 x))) (equal rot (cdr (assoc 50 d)) 1e-8))
    (if (bht:kh-extra-label-p e)
      (l126-check (strcat "actual-stack-spacing-" mode "-" (nth 5 x))
        (equal (cdr (assoc 11 d)) (polar base (- rot (/ pi 2.0)) (* (if (bht:kh-station-label-p e) 2 1) 1.5 h)) 1e-8)))))
(setq manual-point '(140.0 125.0 0.0) d (entget title))
(entmod (bht:dxf-put (bht:dxf-put (bht:dxf-put d 10 manual-point) 11 manual-point) 50 0.22))
(bht:api-sign-display "3" "1" "PARALLEL")
(l126-check "manual-label-location-and-angle-kept" (and (equal manual-point (cdr (assoc 11 (entget title))) 1e-8) (equal 0.22 (cdr (assoc 50 (entget title))) 1e-8)))
(l126-check "actual-two-post-record-kept" (equal rec (bht:obj-read "LABEL-TWO")))
(princ (strcat "\nL126-FAIL=" (itoa l126-fails)))
