(setq i131-n 0 i131-fail 0)
(defun i131-check (name ok)
  (setq i131-n (1+ i131-n)) (if (not ok) (setq i131-fail (1+ i131-fail)))
  (princ (strcat "\n" (if ok "PASS" "FAIL") " INCREMENTAL131 " name)))
(defun i131-obj (id x / ent pid)
  (setq pid (strcat id "-P") ent (entmakex (list '(0 . "POINT") (cons 10 (list x 2.0 0.0)))))
  (bht:pt-write-xdata ent pid "QA" "1" id 2.0 x 0.0 "BIEN_BAO" "QA" "" "")
  (bht:obj-create id '(("nhom" . "BIEN_BAO") ("ma_hieu" . "P.102") ("phia_duong" . "TRAI")) (list pid) T))
(defun i131-snapshot ()
  (list (bht:rec-all "OBJ") (bht:rec-all "SEG") (bht:rec-all "ROUTE") (bht:rec-all "META")
    (mapcar '(lambda (p) (entget (bht:pv (cdr p) 'ent) '("*"))) (bht:pt-all))
    (mapcar '(lambda (p) (entget (cdr p) '("*"))) (bht:tagged-pairs "*" "BHT_KH" 1))))
(setq i131-route (entmakex '((0 . "LWPOLYLINE") (100 . "AcDbEntity") (100 . "AcDbPolyline") (90 . 2) (70 . 0) (10 0.0 0.0) (10 100.0 0.0))))
(bht:route-create "R08" i131-route "TIM_RANH" 10.0 0.0 nil "QA")
(bht:route-add-mark "R08" 0.0 1000.0 1000.0 "QA" "")
(bht:route-add-mark "R08" 100.0 1100.0 1100.0 "QA" "")
(bht:rec-write "SEG" "DOAN_08" '(("segment_id" . "DOAN_08") ("package_id" . "GOI01") ("package_name" . "QA") ("km_start_m" . "1000") ("km_end_m" . "1100") ("side" . "HAI_BEN") ("route_id" . "")))
(setq i131-i 0)
(repeat 25 (setq i131-i (1+ i131-i)) (i131-obj (strcat "OBJ" (bht:pad0 i131-i 3)) (+ 5.0 i131-i)))
(bht:progress-apply (bht:progress-plan "DOAN_08" "R08"))
(bht:kh-display-transaction 'bht:progress-finish (list "DOAN_08"))
(i131-check "fixture-25-confirmed" (= 25 (length (vl-remove-if-not '(lambda (p) (bht:progress-locked (cdr p))) (bht:rec-all "OBJ")))))
(setq i131-old (bht:rec-all "OBJ") i131-geometry (entget i131-route) i131-points (bht:pt-all))
(entmake '((0 . "BLOCK") (2 . "BHT_QA131") (70 . 0) (10 0.0 0.0 0.0)))
(entmake '((0 . "LINE") (10 0.0 0.0 0.0) (11 1.0 1.0 0.0)))
(entmake '((0 . "ENDBLK")))
(regapp "BHT_KH")
(setq i131-symbol (entmakex '((0 . "INSERT") (2 . "BHT_QA131") (10 12.0 13.0 0.0) (41 . 1.0) (42 . 1.0) (43 . 1.0) (50 . 0.7) (-3 ("BHT_KH" (1000 . "OBJ001") (1000 . "TAY") (1000 . "12") (1000 . "13") (1000 . "0.7") (1000 . "1"))))))
(setq i131-label (entmakex '((0 . "TEXT") (10 14.0 15.0 0.0) (40 . 1.0) (1 . "MANUAL OLD LABEL") (-3 ("BHT_KH" (1000 . "OBJ001") (1000 . "NHAN") (1000 . "TAY") (1000 . "14") (1000 . "15"))))))
(setq i131-symbol-before (entget i131-symbol '("*")) i131-label-before (entget i131-label '("*")))
(i131-obj "OTHER11" 150.0)
(bht:obj-write "OTHER11" (bht:set (bht:obj-read "OTHER11") "doan" "DOAN_11"))
(i131-obj "OBJ026" 50.0)
(bht:obj-write "OBJ026" (bht:set (bht:obj-read "OBJ026") "doan" "DOAN_08"))
(setq i131-before (i131-snapshot) i131-plan (bht:progress-plan "DOAN_08" "R08"))
(i131-check "incremental-plan-selects-only-026" (and (not (eq (car i131-plan) 'LOI)) (= 1 (length (nth 2 i131-plan))) (= "OBJ026" (caar (nth 2 i131-plan)))))
(i131-check "preview-is-read-only" (equal i131-before (i131-snapshot)))
(if (not (eq (car i131-plan) 'LOI))
  (progn
    (setq i131-result (bht:progress-apply i131-plan))
    (i131-check "026-calculated" (and (not (eq (car i131-result) 'LOI)) (= "1050.000" (bht:get (bht:obj-read "OBJ026") "ly_trinh_m"))))
    (setq i131-result (bht:kh-display-transaction 'bht:progress-finish (list "DOAN_08")))
    (i131-check "026-confirmed" (and (not (eq (car i131-result) 'LOI)) (bht:progress-locked (bht:obj-read "OBJ026"))))
    (i131-check "25-records-canonical-unchanged" (not (vl-some '(lambda (p) (not (equal (cdr p) (bht:obj-read (car p))))) i131-old)))
    (i131-check "rtk-and-route-unchanged" (and (equal i131-geometry (entget i131-route)) (equal i131-points (vl-remove-if '(lambda (p) (member (car p) '("OBJ026-P" "OTHER11-P"))) (bht:pt-all)))))
    (i131-check "no-duplicates-or-other-segment-write" (and (= 27 (length (bht:obj-ids))) (equal (cdr (assoc "OTHER11" (car i131-before))) (bht:obj-read "OTHER11"))))
    (setq i131-before (i131-snapshot))
    (setq i131-result (bht:progress-apply (bht:progress-plan "DOAN_08" "R08")))
    (i131-check "empty-calculation-no-writes" (and (eq (car i131-result) 'NO_CHANGE) (equal i131-before (i131-snapshot))))
    (setq i131-result (bht:kh-display-transaction 'bht:progress-finish (list "DOAN_08")))
    (i131-check "repeat-confirmation-no-writes" (and (eq (car i131-result) 'NO_CHANGE) (equal i131-before (i131-snapshot))))))
(defun i131-next ()
  (i131-obj "OBJ027" 60.0) (i131-obj "OBJ028" 70.0)
  (foreach id '("OBJ027" "OBJ028") (bht:obj-write id (bht:set (bht:obj-read id) "doan" "DOAN_08"))))
(i131-next)
(setq i131-before (i131-snapshot) i131-old-write bht:obj-write)
(defun bht:obj-write (id rec) (if (= id "OBJ028") (vl-exit-with-error "QA injected second write failure") (i131-old-write id rec)))
(setq i131-result (bht:progress-apply (bht:progress-plan "DOAN_08" "R08")) bht:obj-write i131-old-write)
(i131-check "calculation-rollback-after-first-write" (and (eq (car i131-result) 'LOI) (equal i131-before (i131-snapshot))))
(setq i131-plan (bht:progress-plan "DOAN_08" "R08"))
(bht:obj-write "OBJ027" (bht:set (bht:obj-read "OBJ027") "ma_hieu" "P.103a"))
(setq i131-before (i131-snapshot) i131-result (bht:progress-apply i131-plan))
(i131-check "stale-preview-rejected-without-overwrite" (and (eq (car i131-result) 'LOI) (equal i131-before (i131-snapshot))))
(bht:progress-apply (bht:progress-plan "DOAN_08" "R08"))
(setq i131-before (i131-snapshot))
(defun bht:obj-write (id rec) (if (= id "OBJ028") (vl-exit-with-error "QA injected confirmation failure") (i131-old-write id rec)))
(setq i131-result (bht:kh-display-transaction 'bht:progress-finish (list "DOAN_08")) bht:obj-write i131-old-write)
(i131-check "confirmation-rollback-restores-locks-and-snapshots" (and (eq (car i131-result) 'LOI) (equal i131-before (i131-snapshot))))
(setq i131-p (bht:pv (bht:pt-find "OBJ001-P" (bht:pt-all)) 'ent) i131-pd (entget i131-p))
(entmod (subst '(10 999.0 2.0 0.0) (assoc 10 i131-pd) i131-pd))
(setq i131-before (i131-snapshot) i131-result (bht:progress-plan "DOAN_08" "R08"))
(i131-check "moved-confirmed-point-blocks-addition" (and (eq (car i131-result) 'LOI) (equal i131-before (i131-snapshot))))
(entmod i131-pd)
(setq i131-rd (entget i131-route))
(entmod (subst '(10 -10.0 0.0) (assoc 10 i131-rd) i131-rd))
(setq i131-before (i131-snapshot) i131-result (bht:progress-plan "DOAN_08" "R08"))
(i131-check "edited-route-blocks-addition" (and (eq (car i131-result) 'LOI) (equal i131-before (i131-snapshot))))
(entmod i131-rd)
;; Simulate legacy/raw storage edits without disabling the production guard.
(setq i131-route-record (bht:route-read "R08") i131-old-controls bht:route-controls)
(defun bht:route-controls (rec / value)
  (setq value (i131-old-controls rec))
  (cons (mapcar '(lambda (m) (append (list (car m) (+ 5.0 (cadr m)) (+ 5.0 (caddr m))) (cdddr m))) (car value)) (cdr value)))
(setq i131-before (i131-snapshot) i131-result (bht:progress-plan "DOAN_08" "R08") bht:route-controls i131-old-controls)
(i131-check "changed-controls-with-same-revision-blocked" (and (eq (car i131-result) 'LOI) (equal i131-before (i131-snapshot))))
(setq i131-before (i131-snapshot))
(foreach i131-k '("sign_content" "so_mat" "station_point_method" "doan" "goi" "ma_hieu")
  (setq i131-result (vl-catch-all-apply 'bht:rec-write (list "obj" "obj001" (bht:set (bht:obj-read "OBJ001") i131-k "WRONG"))))
  (i131-check (strcat "guard-" i131-k) (and (vl-catch-all-error-p i131-result) (equal i131-before (i131-snapshot)))))
(setq i131-raw (bht:obj-read "OBJ027"))
(bht:obj-write "OBJ027" (bht:set i131-raw "station_projection_e" "999"))
(setq i131-before (i131-snapshot) i131-result (bht:kh-display-transaction 'bht:progress-finish (list "DOAN_08")))
(i131-check "finish-validates-projection" (and (eq (car i131-result) 'LOI) (equal i131-before (i131-snapshot))))
(bht:obj-write "OBJ027" i131-raw)
(bht:kh-display-transaction 'bht:progress-finish (list "DOAN_08"))
(i131-check "old25-still-unchanged-after-errors" (not (vl-some '(lambda (p) (not (equal (cdr p) (bht:obj-read (car p))))) i131-old)))
(i131-check "manual-symbol-and-label-unchanged" (and (equal i131-symbol-before (entget i131-symbol '("*"))) (equal i131-label-before (entget i131-label '("*")))))
;; Legacy confirmations remain legacy: do not backfill evidence on read/addition.
(foreach i131-pair (bht:rec-all "OBJ")
  (if (bht:progress-locked (cdr i131-pair))
    (bht:rec-write "OBJ" (car i131-pair) (vl-remove-if '(lambda (p) (member (car p) '("progress_context" "progress_route_state"))) (cdr i131-pair)))))
(setq i131-legacy (bht:rec-all "OBJ"))
(i131-obj "LEGACY_ADD" 55.0)
(bht:obj-write "LEGACY_ADD" (bht:set (bht:obj-read "LEGACY_ADD") "doan" "DOAN_08"))
(setq i131-result (bht:progress-apply (bht:progress-plan "DOAN_08" "R08")))
(i131-check "legacy-explicit-controls-allow-addition" (not (eq (car i131-result) 'LOI)))
(bht:kh-display-transaction 'bht:progress-finish (list "DOAN_08"))
(i131-check "legacy-confirmations-never-silently-backfilled" (not (vl-some '(lambda (p) (not (equal (cdr p) (bht:obj-read (car p))))) i131-legacy)))
(princ (strcat "\nINCREMENTAL131-LISP=" (itoa i131-n) " FAIL=" (itoa i131-fail)))
(princ)
