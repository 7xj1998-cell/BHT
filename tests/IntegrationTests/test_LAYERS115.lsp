(setq l115-fail 0)
(defun l115-check (name ok)
  (if (not ok) (setq l115-fail (1+ l115-fail)))
  (princ (strcat "\n" (if qa110-baseline "BASELINE " (if ok "PASS " "FAIL ")) "LAYERS115 " name "=" (if ok "OK" "FAILED"))))
(setq l115-ent (entmakex '((0 . "LWPOLYLINE") (100 . "AcDbEntity") (100 . "AcDbPolyline") (90 . 2) (70 . 0) (10 0.0 0.0) (10 100.0 0.0))))
(bht:route-create "DOAN_11" l115-ent "TIM_DUONG" 20.0 0.0 1 "QA")
(l115-check "new-polyline-layer-uses-route-name" (= "BHT_TUYEN_DOAN_11" (cdr (assoc 8 (entget l115-ent)))))
(bht:route-add-mark "DOAN_11" 0.0 1000.0 1000.0 "QA" "")
(bht:route-add-mark "DOAN_11" 100.0 1100.0 1100.0 "QA" "")
(l115-check "mark-write-keeps-route-layer" (= "BHT_TUYEN_DOAN_11" (cdr (assoc 8 (entget l115-ent)))))
(bht:route-edit "DOAN_11" "DOAN_11_RENAMED" "TIM_DUONG" 20.0 0.0)
(l115-check "rename-uses-final-route-name" (= "BHT_TUYEN_DOAN_11_RENAMED" (cdr (assoc 8 (entget l115-ent)))))
(entmake '((0 . "LAYER") (100 . "AcDbSymbolTableRecord") (100 . "AcDbLayerTableRecord") (2 . "L115_CONFLICT") (70 . 0) (62 . 1) (6 . "Continuous")))
(setq l115-other (entmakex '((0 . "LWPOLYLINE") (100 . "AcDbEntity") (8 . "L115_CONFLICT") (100 . "AcDbPolyline") (90 . 2) (70 . 0) (10 0.0 1.0) (10 100.0 1.0))))
(bht:obj-write "L115_PENDING" '(("object_id" . "L115_PENDING") ("route_id" . "DOAN_11_RENAMED") ("ly_trinh_m" . "1020.000") ("station_status" . "OK")))
(setq l115-before-obj (bht:obj-read "L115_PENDING") l115-before-route (bht:route-read "DOAN_11_RENAMED"))
(setq l115-rejected (vl-catch-all-apply 'bht:route-replace (list "DOAN_11_RENAMED" l115-other)))
(l115-check "replace-layer-conflict-preserves-pending-station" (and (vl-catch-all-error-p l115-rejected) (equal l115-before-obj (bht:obj-read "L115_PENDING")) (equal l115-before-route (bht:route-read "DOAN_11_RENAMED")) (= "L115_CONFLICT" (cdr (assoc 8 (entget l115-other))))))
(bht:rec-delete "OBJ" "L115_PENDING")
(entdel l115-other)
(princ (strcat "\nLAYERS115-DONE FAIL=" (itoa l115-fail)))
(princ "\nQA110-DONE")
(princ)
