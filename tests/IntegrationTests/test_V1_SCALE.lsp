(defun v1-point (id x y group km h / e rec)
 (setq e (entmakex (list '(0 . "POINT") (cons 10 (list x y 0.0)))))
 (bht:pt-write-xdata e id "V1-QA" "1" id (rtos y 2 8) (rtos x 2 8) "0" group "SYNTHETIC_QA" "" "")
 (setq rec (list (cons "object_id" id) (cons "nhom" group) (cons "pt" id)))
 (if km (setq rec (append rec (list (cons "marker_km" km) (cons "marker_h" h)))))
 (bht:obj-write id rec))
(v1-point "A" 0.0 0.0 "COC_TIEU" "10" "0")
(v1-point "B" 100.0 0.0 "COC_TIEU" "10" "1")
(bht:field-save "QA" "QA" "A B" "20" "500" "0.03")
(setq v1-current 0 v1-fails 0 v1-lines nil)
(foreach v1-count '(100 1000 5000)
 (repeat (- v1-count v1-current)
  (setq v1-current (1+ v1-current))
  (v1-point (strcat "S" (itoa v1-current)) (+ 0.01 (* 99.98 (/ (float v1-current) 5000.0))) 3.0 "BIEN_BAO" nil nil))
 (setq v1-times nil)
 (repeat 5
  (setq v1-start (getvar "MILLISECS") v1-result (bht:field-objects))
  (setq v1-times (append v1-times (list (- (getvar "MILLISECS") v1-start)))))
 (setq v1-lines (append v1-lines (list (strcat "count=" (itoa v1-count) " ms=" (vl-prin1-to-string v1-times) " result=" (vl-prin1-to-string v1-result)))))
 (setq v1-i 1 v1-max-error 0.0)
 (repeat v1-count
  (setq v1-rec (bht:obj-read (strcat "S" (itoa v1-i))) v1-expected (+ 10000.01 (* 99.98 (/ (float v1-i) 5000.0))))
  (setq v1-error (abs (- (atof (bht:get v1-rec "ly_trinh_m")) v1-expected)))
  (setq v1-max-error (max v1-max-error v1-error))
  (if (or (> v1-error 0.001) (/= (bht:get v1-rec "field_offset_m") "3.000")) (setq v1-fails (1+ v1-fails)))
  (setq v1-i (1+ v1-i)))
 (setq v1-lines (append v1-lines (list (strcat "max-error-m=" (rtos v1-max-error 2 8)))))
 (setq v1-file (open (strcat (getenv "BHT_V1_QA") "/scale-perf.txt") "w" "utf8-bom"))
 (foreach v1-line v1-lines (write-line v1-line v1-file))
 (close v1-file))
(setq v1-file (open (strcat (getenv "BHT_V1_QA") "/scale-perf.txt") "a" "utf8"))
(write-line (strcat "FAIL=" (itoa v1-fails)) v1-file)(close v1-file)
(princ "\nV1-SCALE-COMPLETE")
