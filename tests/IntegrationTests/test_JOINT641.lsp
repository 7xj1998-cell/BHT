(setq joint-fail 0)
(defun joint-check (n ok) (if (not ok) (setq joint-fail (1+ joint-fail))) (princ (strcat "\n" (if ok "PASS JOINT " "FAIL JOINT ") n)))
(bht:obj-create "JOINT-BOARD" '(("nhom" . "KHAC") ("so_tru" . "2") ("mo_ta" . "Bảng hai trụ")) '("HEAD-1" "HEAD-2") T)
(bht:kh-free-apply "JOINT-BOARD" '(5.0 -4.0 0.0) 0.7 nil)
(setq joint-paths (mapcar 'cdr (vl-remove-if-not '(lambda (p) (= (car p) "JOINT-BOARD")) (bht:tagged-pairs "LINE" "BHT_KH" 1))))
(joint-check "shared-rail-and-two-branches" (= 3 (length joint-paths)))
(joint-check "thin-continuous-white-leaders" (vl-every '(lambda (e) (and (= (cdr (assoc 62 (entget e))) 7) (= (cdr (assoc 370 (entget e))) 9) (= (cdr (assoc 6 (entget e))) "Continuous"))) joint-paths))
(setq joint-rail (car (vl-remove-if-not '(lambda (e) (= (nth 2 (bht:xget e "BHT_KH")) "@BHT_RAIL")) joint-paths)))
(setq joint-mid (mapcar '(lambda (a b) (/ (+ a b) 2.0)) (cdr (assoc 10 (entget joint-rail))) (cdr (assoc 11 (entget joint-rail)))))
(joint-check "both-branches-meet-rail-midpoint" (vl-every '(lambda (e) (equal (cdr (assoc 11 (entget e))) joint-mid 1e-7)) (vl-remove joint-rail joint-paths)))
(setq joint-origins (vl-remove-if-not '(lambda (p) (= (car p) "JOINT-BOARD")) (bht:tagged-pairs "INSERT" "BHT_SIGN_ORIGIN" 1)))
(joint-check "other-board-two-origin-disks" (= 2 (length joint-origins)))
(setq joint-insert (cdr (assoc "JOINT-BOARD" (bht:tagged-pairs "INSERT" "BHT_KH" 1))) joint-blk (cdr (assoc 2 (entget joint-insert))) joint-e (tblobjname "BLOCK" joint-blk) joint-dots 0)
(while (and (setq joint-e (entnext joint-e)) (/= (cdr (assoc 0 (entget joint-e))) "ENDBLK"))
 (setq joint-d (entget joint-e))
 (if (and (= (cdr (assoc 0 joint-d)) "LWPOLYLINE") (= (cdr (assoc 90 joint-d)) 2) (= (cdr (assoc 70 joint-d)) 1)) (setq joint-dots (1+ joint-dots))))
(joint-check "no-filled-feet-in-two-post-block" (= joint-dots 0))
(setq joint-before (mapcar '(lambda (e) (entget e '("BHT_KH"))) joint-paths))
(bht:symbol-sync '("JOINT-BOARD"))
(joint-check "elbow-refresh-idempotent" (equal joint-before (mapcar '(lambda (e) (entget e '("BHT_KH"))) joint-paths)))
(joint-check "survey-unchanged" (equal heading-rtk (list (entget heading-p1 '("BHT_PT")) (entget heading-p2 '("BHT_PT")))))
(setq joint-hidden 0 joint-e (tblobjname "BLOCK" joint-blk))
(while (and (setq joint-e (entnext joint-e)) (/= (cdr (assoc 0 (entget joint-e))) "ENDBLK"))
 (setq joint-d (entget joint-e))
 (if (and (= (cdr (assoc 0 joint-d)) "CIRCLE") (= (cdr (assoc 60 joint-d)) 1)) (setq joint-hidden (1+ joint-hidden))))
(joint-check "both-foot-circles-invisible" (= joint-hidden 2))
(setq joint-raw (BHTSIGNFEET joint-blk)
      joint-anchor (list (cdr (assoc 10 (entget joint-insert))) (cdr (assoc 41 (entget joint-insert))) (cdr (assoc 50 (entget joint-insert)))))
(joint-check "rail-connects-real-feet"
 (and (equal (cdr (assoc 10 (entget joint-rail))) (bht:kh-foot-world (list (nth 0 joint-raw) (nth 1 joint-raw) (nth 2 joint-raw)) joint-anchor) 1e-7)
      (equal (cdr (assoc 11 (entget joint-rail))) (bht:kh-foot-world (list (nth 3 joint-raw) (nth 4 joint-raw) (nth 5 joint-raw)) joint-anchor) 1e-7)))
(bht:kh-free-apply "JOINT-BOARD" '(5.0 -4.0 0.0) 0.7 '((3.0 -6.0 0.0)))
(joint-check "manual-waypoint-removes-automatic-rail" (null (entget joint-rail)))
(setq joint-manual (mapcar 'cdr (vl-remove-if-not '(lambda (p) (= (car p) "JOINT-BOARD")) (bht:tagged-pairs "LWPOLYLINE" "BHT_KH" 1))))
(joint-check "manual-waypoint-retained" (and (= (length joint-manual) 2) (vl-every '(lambda (e) (equal (cadr (mapcar 'cdr (vl-remove-if-not '(lambda (d) (= (car d) 10)) (entget e)))) '(3.0 -6.0) 1e-7)) joint-manual)))
(bht:kh-free-apply "JOINT-BOARD" '(5.0 -4.0 0.0) 0.7 nil)
(joint-check "automatic-restored-removes-old-polylines" (vl-every '(lambda (e) (null (entget e))) joint-manual))
(princ (strcat "\nJOINT-FAIL=" (itoa joint-fail)))
