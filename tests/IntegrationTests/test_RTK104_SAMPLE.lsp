(vl-load-com)
(setq qa-fails 0 qa-checks 0)
(defun s104-check (name ok)
 (setq qa-checks (1+ qa-checks)) (if (not ok) (setq qa-fails (1+ qa-fails)))
 (princ (strcat "\n" (if ok "PASS SAMPLE104 " "FAIL SAMPLE104 ") name)))
(defun s104-labels () (mapcar 'cdr (bht:tagged-pairs "TEXT" "BHT_NHAN" 1)))
(defun s104-snapshot () (mapcar '(lambda (e) (entget e '("*"))) (s104-labels)))
(defun s104-content () (mapcar '(lambda (e / d) (setq d (entget e)) (list (assoc 5 d) (assoc 1 d) (assoc 7 d) (assoc 40 d))) (s104-labels)))
(defun s104-symbols () (mapcar '(lambda (pr) (entget (cdr pr) '("*"))) (bht:tagged-pairs "INSERT" "BHT_KH" 1)))
(setq qa-pts (bht:pt-all) qa-objs (bht:rec-all "OBJ") qa-symbols (s104-symbols)
 qa-labels (s104-snapshot) qa-content (s104-content))
(princ (strcat "\nSAMPLE104 points=" (itoa (length qa-pts)) " labels=" (itoa (length qa-labels)) " objects=" (itoa (length qa-objs))))
(s104-check "nonempty-survey" (and (> (length qa-pts) 100) (> (length qa-labels) 100)))
(princ)
