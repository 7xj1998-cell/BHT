(setq p125-n 0 p125-fail 0)
(defun p125-check (name ok) (setq p125-n (1+ p125-n)) (if (not ok) (setq p125-fail (1+ p125-fail))) (princ (strcat "\n" (if ok "PASS PROGRESS125 " "FAIL PROGRESS125 ") name)))
(setq p125-before (bht:rec-all "OBJ") p125-plan (bht:progress-plan "DOAN_10" "TIMRANHD10"))
(p125-check "real-plan-valid-and-read-only" (and (not (eq (car p125-plan) 'LOI)) (equal p125-before (bht:rec-all "OBJ"))))
(p125-check "real-wrong-road-side-requires-review" (null (assoc "OBJ-000058" (nth 2 p125-plan))))
(p125-check "real-manually-assigned-sign-is-included" (assoc "OBJ-000060" (nth 2 p125-plan)))
(setq p125-result (bht:progress-apply p125-plan))
(p125-check "real-stage-calculates-without-reentering-signs" (and (not (eq (car p125-result) 'LOI)) (> (length (nth 2 p125-plan)) 0) (= (bht:get (bht:obj-read "OBJ-000057") "doan") "DOAN_10")))
(p125-check "real-excluded-sign-unchanged" (equal (cdr (assoc "OBJ-000058" p125-before)) (bht:obj-read "OBJ-000058")))
(setq p125-result (bht:kh-display-transaction 'bht:progress-finish (list "DOAN_10")))
(princ (strcat "\nREAL125-CONFIRM=" (vl-prin1-to-string p125-result)))
(p125-check "real-outside-route-markers-block-confirmation" (and (eq (car p125-result) 'LOI) (not (bht:progress-locked (bht:obj-read "OBJ-000057")))))
;; Isolate invalid legacy assignments in this disposable copy only.
(foreach id '("OBJ-000182" "OBJ-000183" "OBJ-000184") (bht:obj-write id (bht:seg-clear (bht:obj-read id) "CHUA_PHAN_DOAN" "")))
(setq p125-result (bht:kh-display-transaction 'bht:progress-finish (list "DOAN_10")))
(p125-check "real-eligible-results-can-be-confirmed" (and (not (eq (car p125-result) 'LOI)) (bht:progress-locked (bht:obj-read "OBJ-000057"))))
(setq p125-lock (bht:obj-read "OBJ-000057"))
(bht:route-recalculate "TIMRANHD10")
(p125-check "real-legacy-recalc-keeps-confirmed-result" (equal p125-lock (bht:obj-read "OBJ-000057")))
(princ (strcat "\nPROGRESS125-REAL=" (itoa p125-n) " FAIL=" (itoa p125-fail))) (princ)
