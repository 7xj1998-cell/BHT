;; Run only on a copy. TUYEN1 is the real saved reference; 20 is a QA distance.
(defun c107-angles ()
  (mapcar '(lambda (pr / d) (setq d (entget (cdr pr)))
    (list (car pr) (assoc 41 d) (assoc 42 d) (assoc 43 d) (assoc 50 d)))
    (bht:tagged-pairs "INSERT" "BHT_KH" 1)))
(defun c107-check (name ok)
  (if (not ok) (setq c107-fail (1+ c107-fail)))
  (princ (strcat "\nSAMPLE-CENTER107-" name (if ok "-PASS" "-FAIL"))))
(setq c107-fail 0 c107-points (bht:pt-all) c107-records (bht:rec-all "OBJ")
      c107-routes (bht:rec-all "ROUTE") c107-chains (bht:rec-all "FIELD_CHAIN")
      c107-angle (c107-angles) c107-route (bht:route-read "TUYEN1") c107-ent (bht:route-ent c107-route))
(c107-check "REFERENCE" (and (= "KHAC" (bht:get c107-route "loai")) (bht:kh-road-valid-p c107-ent)))
(setq c107-start (getvar "MILLISECS") c107-result (bht:api-symbol-center "TUYEN1" "20" "GAP_KHUC") c107-ms (- (getvar "MILLISECS") c107-start))
(princ c107-result)
(c107-check "APPLY" (and (= "OK" (car c107-result)) (= "TUYEN1" (bht:meta "symbol_center_route" "")) (= "CENTER" (bht:meta "symbol_layout_method" ""))))
(c107-check "POINTS-ANGLES-SCALES" (and (equal c107-points (bht:pt-all)) (equal c107-angle (c107-angles))))
(c107-check "ROUTES-MARKS-CHAINS" (and (equal c107-routes (bht:rec-all "ROUTE")) (equal c107-chains (bht:rec-all "FIELD_CHAIN"))))
(c107-check "CHAINAGE" (vl-every '(lambda (pair / before after) (setq before (cdr pair) after (bht:obj-read (car pair)))
  (vl-every '(lambda (key) (equal (bht:get before key) (bht:get after key)))
    '("ly_trinh_m" "ly_trinh_km" "route_id" "field_chain_id" "station_status" "trang_thai_km" "phia_duong" "phia_tuyen"))) c107-records))
(setq c107-moved 0 c107-bad 0)
(foreach pair c107-records
  (setq id (car pair) before (cdr pair) after (bht:obj-read id))
  (if (or (/= (bht:get before "kh_free_x") (bht:get after "kh_free_x"))
          (/= (bht:get before "kh_free_y") (bht:get after "kh_free_y")))
    (progn
      (setq c107-moved (1+ c107-moved)
            entities (mapcar 'cdr (vl-remove-if-not '(lambda (pr) (= (car pr) id)) (append (bht:tagged-pairs "INSERT" "BHT_KH" 1) (bht:tagged-pairs "TEXT" "BHT_KH" 1))))
            bounds (BHTDISPLAYBOUNDS entities))
      (if bounds
        (progn
          (setq center (list (/ (+ (car bounds) (nth 2 bounds)) 2.0) (/ (+ (cadr bounds) (nth 3 bounds)) 2.0) 0.0)
                radius (/ (distance (list (car bounds) (cadr bounds)) (list (nth 2 bounds) (nth 3 bounds))) 2.0))
          (if (< (- (cadr (bht:curve-project c107-ent center)) radius) (- 20.0 1e-6)) (setq c107-bad (1+ c107-bad))))
        (setq c107-bad (1+ c107-bad))))))
(c107-check "CLEARANCE" (and (> c107-moved 0) (= c107-bad 0)))
(princ (strcat "\nSAMPLE-CENTER107 points=" (itoa (length c107-points)) " records=" (itoa (length c107-records))
  " moved=" (itoa c107-moved) " bad=" (itoa c107-bad) " ms=" (itoa c107-ms) " FAIL=" (itoa c107-fail)))
(princ)
