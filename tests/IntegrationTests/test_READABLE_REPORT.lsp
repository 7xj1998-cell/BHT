(setq report-pass 0 report-fail 0)
(defun rc (name ok) (if ok (setq report-pass (1+ report-pass)) (setq report-fail (1+ report-fail))) (princ (strcat "\n" (if ok "PASS REPORT " "FAIL REPORT ") name)))
(setq empty-result (bht:check))
(rc "empty-drawing-no-errors" (= 0 (car empty-result)))
(setq pt (entmakex '((0 . "POINT") (10 10.0 20.0 0.0))))
(bht:pt-write-xdata pt "MOVED-PT" "QA" "1" "1" 20.0 10.0 0.0 "BIEN_BAO" "QA" "" "")
(entmod (subst '(10 11.0 20.0 0.0) (assoc 10 (entget pt)) (entget pt)))
(entmake '((0 . "BLOCK") (2 . "REPORT_FIXTURE") (70 . 0) (10 0.0 0.0 0.0)))
(entmake '((0 . "CIRCLE") (10 0.0 0.0 0.0) (40 . 0.1)))
(entmake '((0 . "ENDBLK")))
(setq sym (entmakex '((0 . "INSERT") (2 . "REPORT_FIXTURE") (10 5.0 5.0 0.0))))
(bht:xset sym "BHT_KH" '("MISSING-OBJECT"))
(setq photo (entmakex '((0 . "INSERT") (2 . "REPORT_FIXTURE") (10 6.0 6.0 0.0))))
(bht:xset photo "BHT_ANHPT" '("MISSING-PHOTO"))
(setq label (entmakex '((0 . "TEXT") (10 5.0 5.0 0.0) (40 . 1.0) (1 . "OLD POINT"))))
(bht:xset label "BHT_NHAN" '("MISSING-POINT" "TEN"))
(setq before (mapcar '(lambda (e) (entget e '("*"))) (list pt sym photo label)))
(setq checked (bht:check) message (bht:join (caddr checked) "\n"))
(rc "one-moved-point-error" (= 1 (car checked)))
(rc "three-missing-record-warnings" (= 3 (cadr checked)))
(rc "plain-sign-link-description" (vl-string-search "Ký hiệu không tìm thấy hồ sơ đối tượng: 1" message))
(rc "plain-photo-link-description" (vl-string-search "Ký hiệu không tìm thấy hồ sơ ảnh: 1" message))
(rc "plain-point-link-description" (vl-string-search "Nhóm nhãn không tìm thấy điểm gốc: 1" message))
(rc "point-error-action" (vl-string-search "Đối chiếu số liệu gốc" message))
(rc "photo-error-action" (vl-string-search "Cập nhật ký hiệu ảnh" message))
(rc "no-orphan-jargon" (not (vl-string-search "mồ côi" message)))
(rc "check-does-not-move-or-delete" (equal before (mapcar '(lambda (e) (entget e '("*"))) (list pt sym photo label))))
(setq reply (bht:api-check))
(rc "API-count-contract-retained" (and (= "OK" (car reply)) (= "loi=1" (cadr reply)) (= "canh_bao=3" (caddr reply))))
(princ (strcat "\nREPORT-PASS=" (itoa report-pass) " REPORT-FAIL=" (itoa report-fail)))
(princ)
