(setq d105-checks 0 d105-fails 0)
(defun d105-check (name ok) (setq d105-checks (1+ d105-checks)) (if (not ok) (setq d105-fails (1+ d105-fails))) (princ (strcat "\n" (if ok "PASS DISPLAY105 " "FAIL DISPLAY105 ") name)))
(defun d105-leaders () (append (bht:tagged-pairs "LINE" "BHT_KH" 1) (bht:tagged-pairs "LWPOLYLINE" "BHT_KH" 1)))
(setq d105-points (bht:pt-all) d105-records (bht:rec-all "OBJ") d105-meta (bht:rec-read "META" "CONFIG"))
(d105-check "invalid-mode-preserves-config-and-records" (and (= "LOI" (car (bht:api-symbol-display "6" "BAD"))) (equal d105-meta (bht:rec-read "META" "CONFIG")) (equal d105-records (bht:rec-all "OBJ"))))
(d105-check "invalid-gap-does-not-save-mode" (and (= "LOI" (car (bht:api-symbol-display "-1" "THANG"))) (equal d105-meta (bht:rec-read "META" "CONFIG"))))
(setq d105-shapes (mapcar '(lambda (pr / d) (setq d (entget (cdr pr))) (list (car pr) (assoc 10 d) (assoc 41 d))) (bht:tagged-pairs "INSERT" "BHT_KH" 1)))
(d105-check "straight-mode-api" (= "OK" (car (bht:api-symbol-display "6" "THANG"))))
(d105-check "straight-mode-all-leaders-are-lines" (and (>= (length (d105-leaders)) 2) (null (bht:tagged-pairs "LWPOLYLINE" "BHT_KH" 1))))
(d105-check "mode-keeps-positions-and-scales" (equal d105-shapes (mapcar '(lambda (pr / d) (setq d (entget (cdr pr))) (list (car pr) (assoc 10 d) (assoc 41 d))) (bht:tagged-pairs "INSERT" "BHT_KH" 1)) 1e-8))
(bht:symbol-sync nil)
(d105-check "straight-mode-kept-on-symbol-update" (and (= "THANG" (bht:meta "symbol_leader_mode" "")) (null (bht:tagged-pairs "LWPOLYLINE" "BHT_KH" 1))))
(d105-check "bent-mode-api" (= "OK" (car (bht:api-symbol-display "6" "GAP_KHUC"))))
(d105-check "bent-mode-restores-bends" (bht:tagged-pairs "LWPOLYLINE" "BHT_KH" 1))
(setq d105-mode-meta (bht:rec-read "META" "CONFIG") d105-mode-records (bht:rec-all "OBJ") d105-mode-ents (mapcar '(lambda (pr) (entget (cdr pr) '("*"))) (bht:tagged-pairs "*" "BHT_KH" 1)) d105-writer (eval 'bht:kh-leader-sync-source))
(defun bht:kh-leader-sync-source (oid a b ents via source) (/ 1 0))
(setq d105-result (bht:api-symbol-display "8" "THANG"))
(set 'bht:kh-leader-sync-source d105-writer)
(d105-check "failed-mode-change-rolls-back-everything" (and (= "LOI" (car d105-result)) (equal d105-mode-meta (bht:rec-read "META" "CONFIG")) (equal d105-mode-records (bht:rec-all "OBJ")) (equal d105-mode-ents (mapcar '(lambda (pr) (entget (cdr pr) '("*"))) (bht:tagged-pairs "*" "BHT_KH" 1)))))
(d105-check "survey-points-kept" (equal d105-points (bht:pt-all)))
(bht:obj-create "TWO" '(("nhom" . "BIEN_BAO") ("ma_hieu" . "W.209") ("so_tru" . "2")) '("P1" "P2") T)
(bht:kh-free-apply "TWO" '(40.0 44.0 0.0) 1.1 nil)
(d105-check "two-post-straight-mode" (and (= "OK" (car (bht:api-symbol-display "6" "THANG"))) (null (bht:tagged-pairs "LWPOLYLINE" "BHT_KH" 1))))
(setq d105-picker (eval 'bht:kh-pick-target))
(defun bht:kh-pick-target (source cursor) '(26.0 40.0 0.0))
(bht:kh-place-options "O1" "DIRECT" "ANGLE" "37")
(d105-check "placement-direct-stores-straight-mode" (= "THANG" (bht:get (bht:obj-read "O1") "kh_leader_mode")))
(d105-check "placement-direct-does-not-create-bend" (null (assoc "O1" (bht:tagged-pairs "LWPOLYLINE" "BHT_KH" 1))))
(bht:kh-place-options "O1" "ELBOW" "ANGLE" "37")
(d105-check "placement-elbow-overrides-global-straight" (and (= "THANG" (bht:meta "symbol_leader_mode" "")) (= "GAP_KHUC" (bht:get (bht:obj-read "O1") "kh_leader_mode")) (assoc "O1" (bht:tagged-pairs "LWPOLYLINE" "BHT_KH" 1))))
(set 'bht:kh-pick-target d105-picker)
(bht:kh-free-apply-mode "O1" '(26.0 40.0 0.0) 0.6 '((25.0 32.0 0.0)) "WAYPOINT")
(d105-check "manual-waypoint-overrides-global-straight" (and (= "WAYPOINT" (bht:get (bht:obj-read "O1") "kh_leader_mode")) (assoc "O1" (bht:tagged-pairs "LWPOLYLINE" "BHT_KH" 1))))
(bht:symbol-sync '("O1"))
(d105-check "per-object-mode-kept-on-update" (and (= "WAYPOINT" (bht:get (bht:obj-read "O1") "kh_leader_mode")) (assoc "O1" (bht:tagged-pairs "LWPOLYLINE" "BHT_KH" 1))))
(bht:api-symbol-display "6" "THANG")
(d105-check "apply-all-overwrites-individual-mode" (and (vl-every '(lambda (r) (= "THANG" (bht:get (cdr r) "kh_leader_mode"))) (bht:rec-all "OBJ")) (null (bht:tagged-pairs "LWPOLYLINE" "BHT_KH" 1))))
(d105-check "all-placement-modes-keep-survey" (equal d105-points (bht:pt-all)))
(bht:obj-create "LIGHT105" '(("nhom" . "DEN_CS")) '("P1") T)
(bht:kh-free-apply-mode "LIGHT105" '(30.0 42.0 0.0) 0.7 nil "THANG")
(d105-check "light-direct-mode" (null (assoc "LIGHT105" (bht:tagged-pairs "LWPOLYLINE" "BHT_KH" 1))))
(bht:kh-free-apply-mode "LIGHT105" '(30.0 42.0 0.0) 0.7 nil "GAP_KHUC")
(d105-check "light-elbow-mode" (assoc "LIGHT105" (bht:tagged-pairs "LWPOLYLINE" "BHT_KH" 1)))
(bht:api-symbol-display "6" "THANG")
(princ (strcat "\nDISPLAY105-CHECKS=" (itoa d105-checks) " FAIL=" (itoa d105-fails)))
(princ)
