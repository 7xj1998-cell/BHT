(setq f101 (open (getenv "BHT101_REPORT") "w" "utf8-bom"))
(defun v101-check (ok name) (write-line (strcat (if ok "PASS " "FAIL ") name) f101))
(defun v101-placement (/ out d)
 (foreach pair (bht:tagged-pairs "INSERT" "BHT_KH" 1)
  (setq d (entget (cdr pair) '("*")))
  (setq out (cons (vl-remove-if '(lambda (p) (= (car p) 2)) d) out))) out)
(setq v101-points (bht:pt-all) v101-objects (bht:rec-all "OBJ") v101-place (v101-placement))
(setq v101-off nil v101-on nil)
(repeat 5
 (setq v101-start (getvar "MILLISECS") v101-result (bht:api-sign-fill "0"))
 (setq v101-off (append v101-off (list (- (getvar "MILLISECS") v101-start))))
 (v101-check (= (car v101-result) "OK") (strcat "fill off " (vl-prin1-to-string v101-result)))
 (setq v101-start (getvar "MILLISECS") v101-result (bht:api-sign-fill "1"))
 (setq v101-on (append v101-on (list (- (getvar "MILLISECS") v101-start))))
 (v101-check (= (car v101-result) "OK") (strcat "fill on " (vl-prin1-to-string v101-result))))
(write-line (strcat "off_ms=" (vl-prin1-to-string v101-off)) f101)
(write-line (strcat "on_ms=" (vl-prin1-to-string v101-on)) f101)
(v101-check (equal v101-points (bht:pt-all)) "survey points unchanged")
(v101-check (equal v101-objects (bht:rec-all "OBJ")) "object records unchanged")
(v101-check (equal v101-place (v101-placement)) "symbol handles placement rotation scale xdata unchanged")
(if (bht:fn-defined-p 'BHTSIGNFILLALL)
 (progn
  (v101-check (= "1" (bht:meta "sign_fill_all" "")) "fill meta committed")
  (v101-check (= (car (bht:api-sign-fill "invalid")) "LOI") "invalid request rejected")
  (v101-check (= "1" (bht:meta "sign_fill_all" "")) "invalid request preserves meta")
  (foreach name '(c:11 c:22 c:33 c:55 c:BHTLAYFRZ) (v101-check (bht:fn-defined-p name) (strcat "shortcut registered " (vl-prin1-to-string name))))))
(close f101)
(princ "\nV101-FILL-COMPLETE")
