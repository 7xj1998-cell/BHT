(defun qa132-point (id x y / ent)
  (setq ent (entmakex (list '(0 . "POINT") (cons 10 (list x y 0.0)))))
  (bht:pt-write-xdata ent id "QA132" "1" id y x 0.0 "BIEN_BAO" "QA" "" ""))
(setq qa132-route (entmakex '((0 . "LWPOLYLINE") (100 . "AcDbEntity") (100 . "AcDbPolyline") (90 . 2) (70 . 0) (10 0.0 0.0) (10 100.0 0.0))))
(bht:route-create "R01" qa132-route "TIM_DUONG" 20.0 0.0 nil "QA")
(bht:route-add-mark "R01" 0.0 1000.0 1000.0 "QA" "")
(bht:route-add-mark "R01" 100.0 1100.0 1100.0 "QA" "")
(bht:rec-write "SEG" "DOAN_01" '(("segment_id" . "DOAN_01") ("package_id" . "GOI_01") ("km_start_m" . "1000") ("km_end_m" . "1100") ("side" . "HAI_BEN") ("route_id" . "")))
(bht:rec-write "SEG" "DOAN_02" '(("segment_id" . "DOAN_02") ("package_id" . "GOI_02") ("km_start_m" . "1050") ("km_end_m" . "1100") ("side" . "HAI_BEN") ("route_id" . "R01")))
(setq qa132-i 0)
(repeat 50
  (setq qa132-i (1+ qa132-i) qa132-id (strcat "OBJ" (bht:pad0 qa132-i 3)))
  (qa132-point (strcat qa132-id "-P") (+ 5.0 qa132-i) 2.0)
  (bht:obj-create qa132-id '(("nhom" . "BIEN_BAO") ("ma_hieu" . "P.102") ("so_tru" . "1") ("so_mat" . "1")) (list (strcat qa132-id "-P")) T))
(bht:progress-apply (bht:progress-plan "DOAN_01" "R01"))
(bht:kh-display-transaction 'bht:progress-finish (list "DOAN_01"))
(bht:meta-set "progress_active_segment" "DOAN_15")
(qa132-point "NEW-RTK" 80.0 -3.0)
(qa132-point "OUT-RTK" 150.0 2.0)
(qa132-point "ALT-A" 20.0 8.0)
(qa132-point "ALT-B" 40.0 2.0)
(bht:symbol-sync '("OBJ001"))
;; Preserve an intentionally moved/rotated/scaled symbol through correction.
(setq qa132-symbol (cdar (bht:tagged-pairs "INSERT" "BHT_KH" 1)))
(setq qa132-d (entget qa132-symbol))
(entmod (bht:dxf-put (bht:dxf-put (bht:dxf-put (bht:dxf-put (bht:dxf-put qa132-d 10 '(25.0 20.0 0.0)) 50 0.7) 41 1.5) 42 1.5) 43 1.5))
(defun qa132-eval (expression / result)
  (setq result (vl-catch-all-apply '(lambda () (eval (read expression))) nil))
  (if (vl-catch-all-error-p result) (list "LOI" (vl-catch-all-error-message result)) (list "OK" (vl-prin1-to-string result))))
(vl-acad-defun 'qa132-eval)
(princ "\nCORRECTION132-FIXTURE-READY")
(princ)
