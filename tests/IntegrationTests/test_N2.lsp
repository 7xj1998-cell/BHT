;;; BHT 1.1.5 - phien N2: MO LAI N_out.dwg (SAVEAS 2018 cua phien N). Du lieu do C# ghi con nguyen; C# = Lisp.
(load "C:/Users/Le Bao/BHT_TEST_V044/t_common.lsp")
(tbegin "N2")
(setq e (tload) ST (t-state-load "net_N") NID (car ST) PH (cadr ST))
(tchk "M00" "nạp BHT-5.0 trên bản vẽ đã lưu ở phiên N" (and (null e) (= *bht-version* "1.1.5") (wcmatch (strcase (getvar "DWGNAME")) "N_OUT*")) (getvar "DWGNAME"))
(setq e (t-netload "BHT.Bridge.dll"))
(t-dump (t-run "N2_L.txt"))
(command "BHTNETDUMP" (t-run "N2_C.txt"))
(setq cmp (t-cmp (t-run "N2_L.txt") (t-run "N2_C.txt")))
(tchk "M01" "sau SAVEAS + mở lại: dump C# = dump Lisp" (car cmp) cmp)
(setq cmp (t-cmp (t-run "N_C3.txt") (t-run "N2_C.txt")))
(tchk "M02" "dữ liệu sau mở lại GIỐNG HỆT cuối phiên N (không mất / đổi dữ liệu)" (car cmp) cmp)
(setq rec (bht:obj-read NID))
(tchk "M03" "hồ sơ do C# tạo còn nguyên: 3 điểm, ảnh đã gắn, ghi chú đã sửa, ký hiệu theo object_id"
      (and rec (= (length (bht:get-all rec "pt")) 3) (member (strcat PH "|DA_XAC_NHAN|THU_CONG") (bht:get-all rec "anh"))
           (= (bht:get rec "ghi_chu") "đã sửa từ C#") (assoc NID (bht:tagged-pairs "INSERT" "BHT_KH" 1)))
      rec)
(setq r (bht:symbol-sync nil))
(tchk "M04" "BHTKYHIEU (Lisp) sau mở lại: không tạo trùng ký hiệu" (and (= (cdr (assoc 'created r)) 0) (= (cdr (assoc 'duplicates r)) 0)) r)
(tend "N2")
(princ)
