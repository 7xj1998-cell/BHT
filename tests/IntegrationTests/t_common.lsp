;;; BHT 1.1.5 - ham dung chung cho cac phien kiem thu Core Console
;;; Moi kiem thu ghi 1 dong: PASS / FAIL / SKIP / BLOCKED <ma> <ten> | chi tiet
(setq *T-DIR* "C:/Users/Le Bao/BHT_TEST_V044/")
(setq *T-LSP* (strcat *T-DIR* "thư mục có dấu/BHT-1.1.5.lsp"))
(setq *T-PASS* 0 *T-FAIL* 0 *T-SKIP* 0)
(defun tlog (s) (write-line s *T-OUT*) (princ (strcat "\n" s)))
(defun tchk (id name ok detail)
  (if ok (setq *T-PASS* (1+ *T-PASS*)) (setq *T-FAIL* (1+ *T-FAIL*)))
  (tlog (strcat (if ok "PASS " "FAIL ") id " " name (if detail (strcat " | " (vl-princ-to-string detail)) ""))))
(defun tskip (id name status reason)
  (setq *T-SKIP* (1+ *T-SKIP*))
  (tlog (strcat status " " id " " name " | " reason)))
(defun tsafe (id name fn / r)
  (setq r (vl-catch-all-apply fn nil))
  (if (vl-catch-all-error-p r)
    (progn (tchk id name nil (strcat "LỖI: " (vl-catch-all-error-message r))) nil)
    r))
(defun rv (res k) (cdr (assoc k res)))
(defun tbegin (name)
  (setq *T-OUT* (open (strcat *T-DIR* "run/result_" name ".txt") "w" "utf8"))
  (tlog (strcat "Phiên " name ": " (getvar "DWGNAME") " | ACADVER=" (getvar "ACADVER") " | LISPSYS="
                (itoa (getvar "LISPSYS")) " | CDATE=" (rtos (getvar "CDATE") 2 6))))
(defun tend (name)
  (tlog (strcat "TONG PHIEN " name ": " (itoa *T-PASS*) " PASS, " (itoa *T-FAIL*) " FAIL, " (itoa *T-SKIP*) " SKIP/BLOCKED"))
  (close *T-OUT*))
(defun tload (/ r)
  (setq r (vl-catch-all-apply 'load (list *T-LSP*)))
  (if (vl-catch-all-error-p r) (vl-catch-all-error-message r) nil))
;; dem thuc the theo loc
(defun tcount (flt / ss) (setq ss (ssget "_X" flt)) (if ss (sslength ss) 0))
;; --- bo sung 0.3.3 ---
(defun t-bht-ent-p (e)
  (vl-some '(lambda (a) (bht:xget e a)) '("BHT_PT" "BHT_RTK" "BHT_NHAN" "BHT_ANHPT" "BHT_ANHTEN" "BHT_ANHRS" "BHT_KH" "BHT_SIGN_ORIGIN" "BHT_ANHDAN")))
(defun t-snapshot (/ e out)
  (setq e (entnext) out nil)
  (while e (if (not (t-bht-ent-p e)) (setq out (cons (entget e) out))) (setq e (entnext e)))
  out)
(defun t-snap-diff (snap / changed missing e)
  (setq changed 0 missing 0)
  (foreach d snap
    (setq e (cdr (assoc -1 d)))
    (cond ((null (entget e)) (setq missing (1+ missing)))
          ((not (equal (entget e) d))
           (setq changed (1+ changed))
           (if (<= changed 3)
             (tlog (strcat "   thay đổi: " (cdr (assoc 0 d)) " " (cdr (assoc 5 d)) " layer " (cdr (assoc 8 d))
                           " | trước: " (vl-princ-to-string (vl-remove-if '(lambda (g) (member g (entget e))) d))
                           " | sau: " (vl-princ-to-string (vl-remove-if '(lambda (g) (member g d)) (entget e)))))))))
  (list (length snap) missing changed))
(defun t-lbl-count (kind / n)
  (setq n 0)
  (foreach p (bht:tagged-pairs "TEXT" "BHT_NHAN" 2) (if (wcmatch (car p) (strcat "*|" kind)) (setq n (1+ n))))
  n)
(defun t-lbl-dups (/ n)
  (setq n 0)
  (foreach g (bht:group-pairs (bht:tagged-pairs "TEXT" "BHT_NHAN" 2)) (if (> (length (cdr g)) 1) (setq n (1+ n))))
  n)
(defun t-lbl-ent (pid kind) (cadr (assoc (strcat (strcase pid) "|" kind) (bht:group-pairs (bht:tagged-pairs "TEXT" "BHT_NHAN" 2)))))
(defun t-lbl-pos (pid kind / e) (if (setq e (t-lbl-ent pid kind)) (cdr (assoc 10 (entget e)))))
(defun t-pt-ent (id) (bht:pv (bht:pt-find id (bht:pt-all)) 'ent))
(defun t-pt-coords (/ out)
  (setq out nil)
  (foreach it (bht:pt-all) (setq out (cons (cons (car it) (cdr (assoc 10 (entget (bht:pv (cdr it) 'ent))))) out)))
  out)
(defun t-mk-count () (length (bht:tagged-pairs "INSERT" "BHT_ANHPT" 1)))
(defun t-kh-ins () (bht:tagged-pairs "INSERT" "BHT_KH" 1))
(defun t-kh-ins-of (oid) (cdr (assoc oid (bht:group-pairs (t-kh-ins)))))
(defun t-move (e dx dy / d p)
  (setq d (entget e) p (cdr (assoc 10 d)))
  (entmod (subst (list 10 (+ (car p) dx) (+ (cadr p) dy) (caddr p)) (assoc 10 d) d)) (entupd e))
(defun t-lbl-str (pid kind / e) (if (setq e (t-lbl-ent pid kind)) (cdr (assoc 1 (entget e))) nil))
(defun t-verify-csv (path ds / recs idx bad p)
  (setq recs (car (bht:csv-records path ds)) idx (bht:pt-all) bad 0)
  (foreach rr recs
    (setq p (bht:pt-find (car rr) idx))
    (if (not (and p (= (bht:pv p 'name) (nth 3 rr)) (= (bht:pv p 'n) (nth 4 rr)) (= (bht:pv p 'e) (nth 5 rr))
                  (= (bht:pv p 'z) (nth 6 rr)) (= (bht:pv p 'desc) (nth 7 rr))
                  (equal (bht:pv p 'xyz) (list (atof (nth 5 rr)) (atof (nth 4 rr)) (atof (nth 6 rr))) 1e-9)))
      (setq bad (1+ bad))))
  (list (length recs) bad))
(defun t-verify-labels (path ds kinds / recs bad n s want)
  (setq recs (car (bht:csv-records path ds)) bad nil n 0)
  (foreach rr recs
    (foreach k kinds
      (setq want (cond ((= k "TEN") (nth 3 rr)) ((= k "MOTA") (nth 7 rr))
                       ((= k "CAODO") (strcat "H = " (nth 6 rr))) ((= k "ID") (car rr))))
      (setq s (t-lbl-str (car rr) k))
      (cond ((= want "") (if s (setq bad (cons (strcat (car rr) "|" k "=co nhan rong") bad))))
            ((/= s want) (setq bad (cons (strcat (car rr) "|" k) bad)))
            (T (setq n (1+ n))))))
  (list n bad))
;; vi tri moi nhan: ((khoa . pos) ...)
(defun t-lbl-positions (/ out)
  (setq out nil)
  (foreach p (bht:tagged-pairs "TEXT" "BHT_NHAN" 2) (setq out (cons (cons (car p) (cdr (assoc 10 (entget (cdr p))))) out)))
  out)
;; so trang thai nhan
(defun t-lbl-states (/ a t2 l s)
  (setq a 0 t2 0 l 0)
  (foreach p (bht:tagged-pairs "TEXT" "BHT_NHAN" 2)
    (setq s (bht:lbl-state (cdr p)))
    (cond ((eq s 'AUTO) (setq a (1+ a))) ((eq s 'TAY) (setq t2 (1+ t2))) (T (setq l (1+ l)))))
  (list a t2 l))
;; dat nhan cua cac diem ve vi tri mac dinh 0.3.2 (de do chong lan "truoc")
(defun t-lbl-to-legacy (pids / st h off idx g ex kinds p pos n)
  (setq st (bht:lbl-settings) h (cdr (assoc 'h st)) off (cdr (assoc 'off st)) idx (bht:pt-all)
        g (bht:group-pairs (bht:tagged-pairs "TEXT" "BHT_NHAN" 2)) n 0)
  (foreach pid (mapcar 'strcase pids)
    (setq p (bht:pt-find pid idx) kinds nil)
    (foreach kd *bht-lbl-kinds* (if (assoc (strcat pid "|" (car kd)) g) (setq kinds (cons (car kd) kinds))))
    (foreach k kinds
      (setq ex (cadr (assoc (strcat pid "|" k) g)) pos (bht:lbl-legacy-pos p k kinds h off))
      (setq d (entget ex))
      (entmod (subst (list 10 (car pos) (cadr pos) (cadddr (assoc 10 d))) (assoc 10 d) d)) (entupd ex) (setq n (1+ n))))
  n)
;; bang SORTENTS cua Model: ((ename . handle_sap) ...)
(defun t-hex (s / v c)
  (setq v 0.0)
  (foreach c (vl-string->list (strcase s))
    (setq v (+ (* v 16.0) (if (<= c 57) (- c 48) (- c 55)))))
  v)
(defun t-sortents (/ br xd sd out cur)
  (setq br (cdr (assoc 330 (entget (tblobjname "BLOCK" "*Model_Space")))) out nil)
  (setq xd (cdr (assoc 360 (member '(102 . "{ACAD_XDICTIONARY") (entget br)))))
  (if (and xd (setq sd (dictsearch xd "ACAD_SORTENTS")))
    (foreach g sd
      (cond ((= (car g) 331) (setq cur (cdr g)))
            ((and (= (car g) 5) cur) (setq out (cons (cons cur (cdr g)) out) cur nil)))))
  out)
(defun t-rank (e se / h) (setq h (cdr (assoc e se))) (t-hex (if h h (cdr (assoc 5 (entget e))))))
(defun t-rank-range (ents se / lo hi r)
  (foreach e ents (setq r (t-rank e se) lo (if lo (min lo r) r) hi (if hi (max hi r) r)))
  (list lo hi))
(defun t-write-state (name alist / sf)
  (setq sf (open (strcat *T-DIR* "run/state_" name ".txt") "w" "utf8"))
  (foreach it alist
    (if (= (car it) "lblpos")
      (foreach pp (cdr it) (write-line (strcat "lbl:" (car pp) "=" (t-ser (cdr pp))) sf))
      (write-line (strcat (car it) "=" (t-ser (cdr it))) sf)))
  (close sf))
(defun t-read-state (name / f l out p lp)
  (setq out nil lp nil)
  (if (setq f (open (strcat *T-DIR* "run/state_" name ".txt") "r" "utf8"))
    (progn (while (setq l (read-line f))
             (setq p (vl-string-search "=" l))
             (if (= (substr l 1 4) "lbl:")
               (setq lp (cons (cons (substr l 5 (- p 4)) (read (substr l (+ p 2)))) lp))
               (setq out (cons (cons (substr l 1 p) (read (substr l (+ p 2)))) out))))
           (close f)))
  (cons (cons "lblpos" lp) out))
(defun t-mk (pid) (cdr (assoc (strcase pid) (bht:group-pairs (bht:tagged-pairs "INSERT" "BHT_ANHPT" 1)))))
;; so diem trong ref bi doi toa do / mat
(defun t-pts-diff (ref / cur n c)
  (setq cur (t-pt-coords) n 0)
  (foreach it ref (setq c (assoc (car it) cur)) (if (not (and c (equal (cdr c) (cdr it) 1e-12))) (setq n (1+ n))))
  n)
(defun t-ser (v / out)
  (cond ((null v) "nil")
        ((= (type v) 'REAL) (rtos v 2 10))
        ((= (type v) 'INT) (itoa v))
        ((= (type v) 'STR) (vl-prin1-to-string v))
        ((= (type v) 'SYM) (vl-symbol-name v))
        ((and (listp v) (cdr v) (atom (cdr v))) (strcat "(" (t-ser (car v)) " . " (t-ser (cdr v)) ")"))
        ((listp v) (setq out "(") (foreach x v (setq out (strcat out (t-ser x) " "))) (strcat out ")"))
        (T (vl-prin1-to-string v))))
;; --- bo sung 0.4.0: plugin .NET ---
(setq *T-BIN* (strcat *T-DIR* "bin/"))
(defun t-netload (dll / r)
  (setq r (vl-catch-all-apply (function (lambda () (command "_.NETLOAD" (strcat *T-BIN* dll))))))
  (if (vl-catch-all-error-p r) (vl-catch-all-error-message r) nil))
(defun t-run (f) (strcat *T-DIR* "run/" f))
;; Dump chuan phia Lisp - CUNG dinh dang voi BHTNETDUMP (C#)
(defun t-dump (path / f p xyz)
  (setq f (open path "w" "utf8"))
  (write-line "#BHT-DUMP 1" f)
  (foreach it (vl-sort (bht:pt-all) '(lambda (a b) (< (car a) (car b))))
    (setq p (cdr it) xyz (bht:pv p 'xyz))
    (write-line (strcat "P|" (bht:pv p 'id) "|" (bht:pv p 'ds) "|" (bht:pv p 'row) "|" (bht:pv p 'name) "|" (bht:pv p 'n) "|" (bht:pv p 'e)
                        "|" (bht:pv p 'z) "|" (bht:pv p 'cls) "|" (bht:pv p 'src) "|" (bht:pv p 'time) "|" (bht:pv p 'desc)
                        "|" (bht:fnum (car xyz) 4) "|" (bht:fnum (cadr xyz) 4) "|" (bht:fnum (caddr xyz) 4)) f))
  (foreach sub '("OBJ" "PHOTO" "DATASET" "META" "ROUTE" "SEG")
    (foreach k (bht:rec-keys sub)
      (write-line (strcat "R|" sub "|" k) f)
      (foreach pr (bht:rec-read sub k) (write-line (strcat "  " (car pr) "=" (cdr pr)) f))))
  (foreach k (bht:rec-keys "PHOTO")
    (write-line (strcat "J|" k "|" (bht:str (bht:photo-path (bht:photo-read k)))) f))
  (close f))
(defun t-lines (path / f l out)
  (setq out nil)
  (if (setq f (open path "r" "utf8"))
    (progn (while (setq l (read-line f)) (setq out (cons l out))) (close f)))
  (setq out (reverse out))
  (if (and out (> (strlen (car out)) 0) (= (ascii (substr (car out) 1 1)) 65279)) (setq out (cons (substr (car out) 2) (cdr out))))
  out)
;; So sanh 2 tep tung dong: (giong? so_dong_A so_dong_B dong_khac_dau_tien)
(defun t-cmp (a b / la lb i d)
  (setq la (t-lines a) lb (t-lines b) i 0 d nil)
  (while (and (null d) la lb)
    (setq i (1+ i))
    (if (/= (car la) (car lb)) (setq d (list i (car la) (car lb))))
    (setq la (cdr la) lb (cdr lb)))
  (setq la (t-lines a) lb (t-lines b))
  (list (and (null d) (= (length la) (length lb)) (> (length la) 1)) (length la) (length lb) d))
(defun t-count-prefix (path pre / n)
  (setq n 0)
  (foreach l (t-lines path) (if (wcmatch l (strcat pre "*")) (setq n (1+ n))))
  n)
(defun t-backups (/ n)
  (setq n 0)
  (foreach sub '("OBJ" "PHOTO" "META" "DATASET")
    (foreach g (entget (bht:subdict sub)) (if (and (= (car g) 3) (wcmatch (cdr g) "*__BHT_CU")) (setq n (1+ n)))))
  n)
(defun t-state-save (name lst / f)
  (setq f (open (strcat *T-DIR* "run/state_" name ".txt") "w" "utf8"))
  (foreach x lst (write-line x f)) (close f))
(defun t-state-load (name) (t-lines (strcat *T-DIR* "run/state_" name ".txt")))
