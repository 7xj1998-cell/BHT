(load (strcat *bht-module-root* "/../../tests/IntegrationTests/label109_helpers.lsp"))
(bht:meta-set "nhan_uu_tien_dt" "0") (bht:meta-set "nhan_id" "1")
(setq p109 (entmakex '((0 . "POINT") (10 30.0 40.0 0.0))))
(bht:pt-write-xdata p109 "PT109" "QA" "1" "207" 40.0 30.0 1.911 "KHAC" "QA" "đường đá dăm" "")
(bht:lbl-sync)
;; Deliberately scatter and mix row angles to reproduce the screenshot.
(foreach pr (bht:tagged-pairs "TEXT" "BHT_NHAN" 1)
 (entmod (bht:dxf-put (bht:dxf-put (entget (cdr pr)) 10 '(99.0 100.0 0.0)) 50 0.4)))
(setq records109 (bht:pt-all))
(bht:photo-write "PHOTO109" '(("photo_id" . "PHOTO109") ("gps_hop_le" . "1") ("lon" . "106.2") ("lat" . "10.6") ("file_name" . "unchanged.jpg") ("doi_tuong" . "SIGN109")))
(bht:photo-sync)
(setq photo109 (bht:photo-read "PHOTO109") marker109 (cdr (assoc "PHOTO109" (bht:tagged-pairs "INSERT" "BHT_ANHPT" 1)))
      gps109 (cdr (assoc 10 (entget marker109))))
(foreach angle109 '(0.0 0.4 1.570796326795 3.14159265359 5.2)
 (l109-check "rotation-API-success" (/= (car (bht:lbl-rotate angle109)) 'LOI))
 (l109-check "scattered-rows-regrouped-in-order" (l109-cluster-p angle109))
 (setq e109 (cdr (assoc "PHOTO109" (bht:tagged-pairs "TEXT" "BHT_ANHTEN" 1))) d109 (entget e109))
 (l109-check "Timemark-caption-and-marker-follow-angle"
   (and (equal (cdr (assoc 50 d109)) angle109 1e-8)
        (equal (cdr (assoc 50 (entget marker109))) angle109 1e-8)
        (equal (cdr (assoc 10 d109)) (bht:photo-caption-position gps109 (bht:photo-scale) angle109) 1e-7)))
 (bht:photo-sync)
 (l109-check "photo-sync-keeps-caption-position-angle" (equal d109 (entget e109) 1e-7)))
(l109-check "survey-and-photo-records-unchanged" (and (equal records109 (bht:pt-all)) (equal photo109 (bht:photo-read "PHOTO109")) (equal gps109 (cdr (assoc 10 (entget marker109))))))
;; Manual markers: label exists with or without a station, no imaginary elevation.
(setq m109 (entmakex '((0 . "POINT") (10 60.0 60.0 0.0))))
(bht:pt-write-xdata m109 "MANUAL109" "MANUAL_CAD" "0" "MARKER109" 60.0 60.0 "" "COC_TIEU" "MANUAL_CAD" "Cọc tiêu bổ sung thủ công" "")
(bht:obj-create "MARKER109" '(("nhom" . "COC_TIEU") ("marker_km" . "49") ("marker_h" . "3")) '("MANUAL109") T)
(bht:obj-write "MARKER109" (bht:set (bht:obj-read "MARKER109") "position_source" "MANUAL_CAD"))
(l109-check "manual-symbol-sync-success" (= "OK" (car (bht:api-symbol-sync "MARKER109"))))
(setq ml109 (mapcar 'cdr (vl-remove-if-not '(lambda (pr) (= (car pr) "MANUAL109")) (bht:tagged-pairs "TEXT" "BHT_NHAN" 1))))
(l109-check "manual-point-H3-49-caption-created"
 (and (vl-some '(lambda (e) (= (cdr (assoc 1 (entget e))) "H3/49")) ml109)
      (not (vl-some '(lambda (e) (member (cadr (bht:xget e "BHT_NHAN")) '("MOTA" "CAODO"))) ml109))))
(l109-check "marker-symbol-label-created"
 (vl-some '(lambda (pr) (and (= (car pr) "MARKER109") (= (cdr (assoc 1 (entget (cdr pr)))) "H3/49"))) (bht:tagged-pairs "TEXT" "BHT_KH" 1)))
(bht:obj-write "MARKER109" (bht:set (bht:set (bht:obj-read "MARKER109") "marker_h" "") "marker_km" ""))
(bht:api-symbol-sync "MARKER109")
(l109-check "unknown-manual-marker-visible-without-fabricated-station"
 (and (= (bht:kh-label "MARKER109" (bht:obj-read "MARKER109")) "Cọc tiêu")
      (= (bht:get (bht:obj-read "MARKER109") "ly_trinh_km") "")
      (vl-some '(lambda (pr) (and (= (car pr) "MANUAL109") (= (cdr (assoc 1 (entget (cdr pr)))) (bht:cad-text "Cọc tiêu" (bht:default-label-style))))) (bht:tagged-pairs "TEXT" "BHT_NHAN" 1))))
;; Line clearance is tested in the actual text bounds, at several angles and scales.
(bht:obj-create "SIGN109" '(("nhom" . "BIEN_BAO") ("ma_hieu" . "W.245a") ("so_tru" . "1")) '("PT109") T)
(bht:obj-write "SIGN109" (bht:set (bht:obj-read "SIGN109") "ly_trinh_km" "Km49+300.00"))
(foreach angle109 '(0.0 0.4 1.570796326795 3.14159265359 5.2)
 (bht:kh-free-apply "SIGN109" '(30.0 50.0 0.0) angle109 nil)
 (setq anchor109 (entget (cdr (assoc "SIGN109" (bht:tagged-pairs "INSERT" "BHT_KH" 1))))
       anchor109 (list (cdr (assoc 10 anchor109)) (cdr (assoc 41 anchor109)) (cdr (assoc 50 anchor109)))
       clear109 T)
 (foreach pr (bht:tagged-pairs "TEXT" "BHT_KH" 1)
  (if (= (car pr) "SIGN109")
   (progn
    (setq d109 (entget (cdr pr)) tb109 (textbox d109) origin109 (bht:kh-caption-local (cdr (assoc 10 d109)) anchor109)
          box109 (list (+ (car origin109) (caar tb109)) (+ (cadr origin109) (cadar tb109)) (+ (car origin109) (caadr tb109)) (+ (cadr origin109) (cadadr tb109))))
    (foreach leader109 (append (bht:tagged-pairs "LINE" "BHT_KH" 1) (bht:tagged-pairs "LWPOLYLINE" "BHT_KH" 1))
     (if (= (car leader109) "SIGN109")
      (progn
       (setq ld109 (entget (cdr leader109)) vs109 (if (= (cdr (assoc 0 ld109)) "LINE") (list (cdr (assoc 10 ld109)) (cdr (assoc 11 ld109)))
          (mapcar '(lambda (v) (list (car v) (cadr v) 0.0)) (mapcar 'cdr (vl-remove-if-not '(lambda (v) (= (car v) 10)) ld109)))))
       (while (cdr vs109)
        (if (bht:segment-box-hit (bht:kh-caption-local (car vs109) anchor109) (bht:kh-caption-local (cadr vs109) anchor109) box109) (setq clear109 nil))
        (setq vs109 (cdr vs109)))))))))
 (l109-check "sign-title-and-station-clear-of-own-leader" clear109))
(bht:lbl-rotate 0.4)
(princ (strcat "\nLABEL109-CHECKS=" (itoa l109-n) " FAIL=" (itoa l109-fail))) (princ)
