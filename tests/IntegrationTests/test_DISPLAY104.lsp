(vl-load-com)
(setq d104-fails 0 d104-checks 0)
(defun d104-check (name ok) (setq d104-checks (1+ d104-checks)) (if (not ok) (setq d104-fails (1+ d104-fails))) (princ (strcat "\n" (if ok "PASS DISPLAY104 " "FAIL DISPLAY104 ") name)))
(d104-check "leader-origin-above-face-uses-side-and-lower-corridor"
 (equal (bht:kh-support-via '(0.0 5.0 0.0) '(0.0 -2.0 0.0) '((0.0 0.0 0.0) 1.0 0.0) '(-1.0 -2.0 1.0 2.0))
        '((1.25 5.0 0.0) (1.25 -2.25 0.0) (0.0 -2.25 0.0)) 1e-8))
(d104-check "leader-corridor-follows-rotated-scaled-block"
 (equal (bht:kh-support-via '(-10.0 0.0 0.0) '(4.0 0.0 0.0) (list '(0.0 0.0 0.0) 2.0 (/ pi 2.0)) '(-1.0 -2.0 1.0 2.0))
        '((-10.0 2.5 0.0) (4.5 2.5 0.0) (4.5 0.0 0.0)) 1e-8))
(foreach row '(("P1" 20.0 30.0) ("P2" 50.0 60.0))
 (setq pt (entmakex (list '(0 . "POINT") (cons 10 (list (cadr row) (caddr row) 0.0)))))
 (bht:pt-write-xdata pt (car row) "QA" "1" (car row) (caddr row) (cadr row) 0.0 "BIEN_BAO" "QA" "" ""))
(bht:obj-create "O1" '(("nhom" . "BIEN_BAO") ("ma_hieu" . "W.209") ("so_tru" . "1")) '("P1") T)
(bht:obj-create "O2" '(("nhom" . "BIEN_BAO") ("ma_hieu" . "P.127-40") ("so_tru" . "1")) '("P2") T)
(bht:kh-free-apply "O1" '(28.0 30.0 0.0) 0.7 nil)
(bht:kh-free-apply "O2" '(53.0 64.0 0.0) 1.3 nil)
(setq d104-points (bht:pt-all) d104-angle-scale
 (mapcar '(lambda (pr / d) (setq d (entget (cdr pr))) (list (car pr) (assoc 50 d) (assoc 41 d))) (bht:tagged-pairs "INSERT" "BHT_KH" 1)))
(setq d104-before (mapcar '(lambda (pr) (entget (cdr pr) '("*"))) (bht:tagged-pairs "*" "BHT_KH" 1)))
(d104-check "invalid-gap-no-change" (and (= (car (bht:api-symbol-gap "-1")) "LOI") (equal d104-before (mapcar '(lambda (pr) (entget (cdr pr) '("*"))) (bht:tagged-pairs "*" "BHT_KH" 1)))))
(setq d104-result (bht:api-symbol-gap "6")) (princ d104-result)
(d104-check "distance-api" (= (car d104-result) "OK"))
(d104-check "uniform-display-distance" (vl-every '(lambda (pr / d source) (setq d (entget (cdr pr)) source (bht:obj-position (bht:obj-read (car pr)) (bht:pt-all))) (equal (distance (list (car source) (cadr source)) (list (cadr (assoc 10 d)) (caddr (assoc 10 d)))) 6.0 1e-7)) (bht:tagged-pairs "INSERT" "BHT_KH" 1)))
(d104-check "rotation-scale-kept" (equal d104-angle-scale (mapcar '(lambda (pr / d) (setq d (entget (cdr pr))) (list (car pr) (assoc 50 d) (assoc 41 d))) (bht:tagged-pairs "INSERT" "BHT_KH" 1)) 1e-8))
(d104-check "points-kept" (equal d104-points (bht:pt-all)))
(d104-check "one-layer-including-leaders-labels-origins" (vl-every '(lambda (pr) (= (cdr (assoc 8 (entget (cdr pr)))) "BHT_KYHIEU")) (append (bht:tagged-pairs "*" "BHT_KH" 1) (bht:tagged-pairs "INSERT" "BHT_SIGN_ORIGIN" 1))))
(setq d104-after (mapcar '(lambda (pr) (entget (cdr pr) '("*"))) (bht:tagged-pairs "*" "BHT_KH" 1)))
(bht:api-symbol-gap "6")
(d104-check "repeat-gap-idempotent" (equal d104-after (mapcar '(lambda (pr) (entget (cdr pr) '("*"))) (bht:tagged-pairs "*" "BHT_KH" 1)) 1e-8))
(setq d104-records (bht:rec-all "OBJ") d104-meta (bht:rec-read "META" "CONFIG") d104-writer (eval 'bht:kh-leader-sync-source))
(defun bht:kh-leader-sync-source (oid a b ents via source) (/ 1 0))
(setq d104-result (bht:api-symbol-gap "9"))
(set 'bht:kh-leader-sync-source d104-writer)
(d104-check "failure-rolls-back-records-and-display" (and (= (car d104-result) "LOI") (equal d104-records (bht:rec-all "OBJ")) (equal d104-meta (bht:rec-read "META" "CONFIG")) (equal d104-after (mapcar '(lambda (pr) (entget (cdr pr) '("*"))) (bht:tagged-pairs "*" "BHT_KH" 1)))))
(setq route (entmakex '((0 . "LWPOLYLINE") (100 . "AcDbEntity") (100 . "AcDbPolyline") (90 . 2) (70 . 0) (10 0.0 0.0) (10 100.0 0.0))))
(bht:route-create "R1" route "TIM_DUONG" 30.0 40000.0 nil "QA")
(bht:rec-write "FIELD_CHAIN" "C1" '(("chain_id" . "C1") ("marker" . "O1") ("marker" . "O2")))
(bht:rec-write "PHOTO" "A1" '(("photo_id" . "A1") ("duong_dan" . "photo.jpg") ("goc" . "C:/photos") ("doi_tuong" . "O1")))
(bht:obj-write "O1" (bht:set (bht:obj-read "O1") "route_id" "R1"))
(entmakex '((0 . "LINE") (10 200.0 200.0 0.0) (11 210.0 200.0 0.0)))
(princ (strcat "\nDISPLAY104-CHECKS=" (itoa d104-checks) " FAIL=" (itoa d104-fails)))
(princ)
