(load (strcat *bht-module-root* "/../../tests/IntegrationTests/label109_helpers.lsp"))
(load (strcat *bht-module-root* "/../../tests/IntegrationTests/test_SAMPLE_LABEL108.lsp"))
(setq sample109-pt (bht:pt-all) sample109-obj (bht:rec-all "OBJ") sample109-photo (bht:rec-all "PHOTO")
      sample109-route (bht:rec-all "ROUTE") sample109-chain (bht:rec-all "FIELD_CHAIN")
      sample109-positions (mapcar '(lambda (pr) (list (car pr) (cdr (assoc 10 (entget (cdr pr)))))) (bht:tagged-pairs "INSERT" "BHT_ANHPT" 1)))
(setq sample109-manual-ids (mapcar 'car (vl-remove-if-not '(lambda (row) (and (= (bht:get (cdr row) "position_source") "MANUAL_CAD") (= (bht:get (cdr row) "nhom") "COC_TIEU"))) sample109-obj)))
(l109-check "sample-create-update-manual-marker-symbols" (= "OK" (car (bht:api-symbol-sync (bht:join sample109-manual-ids ",")))))
(princ (bht:api-label-sync ""))
(setq sample109-start (getvar "MILLISECS") sample109-result (bht:api-label-rotate "UCS") sample109-ms (- (getvar "MILLISECS") sample109-start))
(l109-check "sample-rotation-success" (= (car sample109-result) "OK"))
(l109-check "sample-compact-RTK-and-manual-labels" (l109-cluster-p 0.0))
(setq sample109-photo-labels (bht:tagged-pairs "TEXT" "BHT_ANHTEN" 1))
(l109-check "sample-photo-angle-and-caption"
 (vl-every '(lambda (pr / e d label ld)
   (setq e (cdr pr) d (entget e) label (cdr (assoc (car pr) sample109-photo-labels)) ld (if label (entget label)))
   (or (null label) (and (equal (cdr (assoc 50 ld)) 0.0 1e-8)
      (equal (cdr (assoc 10 ld)) (bht:photo-caption-position (cdr (assoc 10 d)) (abs (cdr (assoc 41 d))) 0.0) 1e-7))))
  (bht:tagged-pairs "INSERT" "BHT_ANHPT" 1)))
(l109-check "sample-survey-records-GPS-and-links-preserved"
 (and (equal sample109-pt (bht:pt-all)) (equal sample109-obj (bht:rec-all "OBJ")) (equal sample109-photo (bht:rec-all "PHOTO"))
      (equal sample109-route (bht:rec-all "ROUTE")) (equal sample109-chain (bht:rec-all "FIELD_CHAIN"))
      (equal sample109-positions (mapcar '(lambda (pr) (list (car pr) (cdr (assoc 10 (entget (cdr pr)))))) (bht:tagged-pairs "INSERT" "BHT_ANHPT" 1)))))
(setq sample109-manual 0 sample109-bad 0)
(foreach row sample109-obj
 (if (and (= (bht:get (cdr row) "position_source") "MANUAL_CAD") (= (bht:get (cdr row) "nhom") "COC_TIEU"))
  (progn
   (setq sample109-manual (1+ sample109-manual))
   (if (not (vl-some '(lambda (pr) (and (= (car pr) (car row)) (= (cdr (assoc 1 (entget (cdr pr)))) (bht:cad-text (bht:kh-label (car row) (cdr row)) (bht:kh-label-style ""))))) (bht:tagged-pairs "TEXT" "BHT_KH" 1)))
     (setq sample109-bad (1+ sample109-bad))))))
(l109-check "sample-manual-marker-captions-present" (and (> sample109-manual 0) (= sample109-bad 0)))
(princ (strcat "\nLABEL109-SAMPLE points=" (itoa (length sample109-pt)) " RTK_labels=" (itoa (length (bht:tagged-pairs "TEXT" "BHT_NHAN" 1)))
 " Timemark_labels=" (itoa (length (bht:tagged-pairs "TEXT" "BHT_ANHTEN" 1))) " manual_coc=" (itoa sample109-manual)
 " objects=" (itoa (length sample109-obj)) " rotate_ms=" (itoa sample109-ms)))
(princ (strcat "\nLABEL109-CHECKS=" (itoa l109-n) " FAIL=" (itoa l109-fail))) (princ)
