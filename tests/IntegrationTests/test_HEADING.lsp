(setq heading-fails 0)
(defun heading-check (name ok) (if (not ok) (setq heading-fails (1+ heading-fails))) (princ (strcat "\n" (if ok "PASS HEADING " "FAIL HEADING ") name)))
(defun heading-insert (oid) (cdr (assoc oid (bht:tagged-pairs "INSERT" "BHT_KH" 1))))
(defun heading-angle (oid) (cdr (assoc 50 (entget (heading-insert oid)))))
(defun heading-same-angle (a b) (and a b (equal (cos a) (cos b) 1e-7) (equal (sin a) (sin b) 1e-7)))
(defun heading-transform (oid / d) (setq d (entget (heading-insert oid))) (list (assoc 10 d) (assoc 41 d) (assoc 42 d) (assoc 43 d)))
(setq heading-pl (entmakex '((0 . "LWPOLYLINE") (100 . "AcDbEntity") (8 . "0") (100 . "AcDbPolyline") (90 . 3) (70 . 0) (10 0.0 0.0) (10 10.0 0.0) (10 10.0 10.0))))
(bht:route-create "HEAD-ROUTE" heading-pl "TIM_DUONG" 4.0 0.0 nil "QA")
(bht:route-write "HEAD-ROUTE" (bht:set (bht:route-read "HEAD-ROUTE") "max_offset" "10"))
(setq heading-p1 (entmakex '((0 . "POINT") (10 5.0 -1.0 0.0))) heading-p2 (entmakex '((0 . "POINT") (10 11.0 5.0 0.0))) heading-p3 (entmakex '((0 . "POINT") (10 50.0 50.0 0.0))))
(bht:pt-write-xdata heading-p1 "HEAD-1" "QA" "1" "1" -1.0 5.0 0.0 "BIEN_BAO" "test" "" "")
(bht:pt-write-xdata heading-p2 "HEAD-2" "QA" "2" "2" 5.0 11.0 0.0 "BIEN_BAO" "test" "" "")
(bht:pt-write-xdata heading-p3 "HEAD-3" "QA" "3" "3" 50.0 50.0 0.0 "BIEN_BAO" "test" "" "")
(bht:obj-create "HEAD-A" '(("nhom" . "BIEN_BAO") ("ma_hieu" . "W.207a") ("so_tru" . "1")) '("HEAD-1") T)
(bht:obj-create "HEAD-B" '(("nhom" . "BIEN_BAO") ("ma_hieu" . "R.415a") ("so_tru" . "1")) '("HEAD-2") T)
(bht:obj-create "HEAD-FAR" '(("nhom" . "BIEN_BAO") ("ma_hieu" . "W.207a")) '("HEAD-3") T)
(bht:obj-create "HEAD-UNPLACED" '(("nhom" . "BIEN_BAO") ("ma_hieu" . "W.207a")) '("HEAD-3") T)
(bht:kh-free-apply "HEAD-A" '(4.0 -4.0 0.0) 0.6 '((4.0 -1.0 0.0)))
(bht:kh-free-apply "HEAD-B" '(14.0 5.0 0.0) 0.3 nil)
(bht:kh-free-apply "HEAD-FAR" '(54.0 50.0 0.0) 0.4 nil)
(setq heading-rtk (list (entget heading-p1 '("BHT_PT")) (entget heading-p2 '("BHT_PT"))) heading-geom (entget heading-pl)
      heading-before (list (heading-transform "HEAD-A") (heading-transform "HEAD-B")) heading-via (bht:kh-via-points (bht:obj-read "HEAD-A"))
      heading-far-before (bht:obj-read "HEAD-FAR"))
(setq heading-result (bht:kh-heading-apply '("HEAD-A" "HEAD-B" "HEAD-A" "HEAD-FAR" "HEAD-UNPLACED") "ROUTE" "HEAD-ROUTE" nil))
(princ (strcat "\nHEADING-FIRST=" (vl-princ-to-string heading-result)))
(heading-check "dedup-two-placed-near-route-others-skipped" (and (= (cdr (assoc 'rotated heading-result)) 2) (= (cdr (assoc 'skipped heading-result)) 2)))
(heading-check "head-east-on-first-route-segment" (heading-same-angle (heading-angle "HEAD-A") (- (/ pi 2.0))))
(heading-check "head-north-on-second-route-segment" (heading-same-angle (heading-angle "HEAD-B") 0.0))
(heading-check "bulk-keeps-position-and-all-scales" (equal heading-before (list (heading-transform "HEAD-A") (heading-transform "HEAD-B"))))
(heading-check "bulk-keeps-RTK-route-and-waypoints" (and (equal heading-rtk (list (entget heading-p1 '("BHT_PT")) (entget heading-p2 '("BHT_PT")))) (equal heading-geom (entget heading-pl)) (equal heading-via (bht:kh-via-points (bht:obj-read "HEAD-A")))))
(heading-check "skipped-record-unchanged-and-no-unplaced-insert" (and (equal heading-far-before (bht:obj-read "HEAD-FAR")) (null (heading-insert "HEAD-UNPLACED"))))
(bht:route-set-start-dir "HEAD-ROUTE" '(10.0 10.0 0.0) -1)
(bht:symbol-sync '("HEAD-A" "HEAD-B"))
(heading-check "route-reverse-updates-both-heads" (and (heading-same-angle (heading-angle "HEAD-A") (/ pi 2.0)) (heading-same-angle (heading-angle "HEAD-B") pi)))
(setq heading-result (bht:kh-heading-apply '("HEAD-A" "HEAD-B") "FIXED" "" (/ pi 2.0)))
(heading-check "fixed-AB-north-both-upright" (and (= (cdr (assoc 'rotated heading-result)) 2) (heading-same-angle (heading-angle "HEAD-A") 0.0) (heading-same-angle (heading-angle "HEAD-B") 0.0)))
(bht:route-set-start-dir "HEAD-ROUTE" '(0.0 0.0 0.0) 1)
(bht:symbol-sync '("HEAD-A" "HEAD-B"))
(heading-check "fixed-heading-kept-on-refresh-route-change" (and (heading-same-angle (heading-angle "HEAD-A") 0.0) (heading-same-angle (heading-angle "HEAD-B") 0.0)))
(setq heading-e (heading-insert "HEAD-A"))
(entmod (bht:dxf-put (entget heading-e) 10 '(3.0 -5.0 0.0)))
(bht:kh-heading-apply '("HEAD-A") "FIXED" "" 0.0)
(heading-check "manual-insert-move-kept-when-bulk-rotating" (and (equal (cdr (assoc 10 (entget heading-e))) '(3.0 -5.0 0.0)) (heading-same-angle (heading-angle "HEAD-A") (- (/ pi 2.0)))))
(setq heading-select (ssadd)) (ssadd heading-e heading-select) (ssadd (cdr (assoc "HEAD-A" (bht:tagged-pairs "INSERT" "BHT_SIGN_ORIGIN" 1))) heading-select)
(heading-check "select-symbol-plus-origin-deduplicates-record" (= (length (bht:kh-heading-selection heading-select)) 1))
(setq heading-before-rec (bht:obj-read "HEAD-A"))
(heading-check "invalid-route-no-mutation" (and (eq (car (bht:kh-heading-apply '("HEAD-A") "ROUTE" "MISSING" nil)) 'LOI) (equal heading-before-rec (bht:obj-read "HEAD-A"))))
(bht:kh-free-apply "HEAD-A" '(3.0 -5.0 0.0) 0.4 nil)
(heading-check "explicit-single-placement-clears-bulk-heading" (and (= (bht:get (bht:obj-read "HEAD-A") "sign_heading_mode") "") (heading-same-angle (heading-angle "HEAD-A") 0.4)))
;; A two-foot CAP1 frame reconnects both survey points after bulk rotation.
(bht:obj-create "HEAD-FRAME" '(("nhom" . "BIEN_BAO") ("ma_hieu" . "R.415a") ("so_tru" . "2") ("sign_layout" . "CAP1_9")) '("HEAD-1" "HEAD-2") T)
(bht:kh-free-apply "HEAD-FRAME" '(20.0 -5.0 0.0) 0.0 nil)
(bht:kh-heading-apply '("HEAD-FRAME") "FIXED" "" 0.0)
(setq heading-feet (BHTSIGNFEET (cdr (assoc 2 (entget (heading-insert "HEAD-FRAME"))))))
(setq heading-feet (mapcar '(lambda (i) (bht:kh-foot-world (list (nth i heading-feet) (nth (1+ i) heading-feet) (nth (+ i 2) heading-feet)) (list '(20.0 -5.0 0.0) (cdr (assoc 41 (entget (heading-insert "HEAD-FRAME")))) (- (/ pi 2.0))))) '(0 3)))
(setq heading-lines (mapcar 'cdr (vl-remove-if-not '(lambda (pair) (= (car pair) "HEAD-FRAME")) (append (bht:tagged-pairs "LINE" "BHT_KH" 1) (bht:tagged-pairs "LWPOLYLINE" "BHT_KH" 1)))))
(heading-check "CAP1-two-leaders-reconnect-to-rotated-feet" (and (= (length heading-lines) 2) (vl-every '(lambda (line) (vl-some '(lambda (foot) (equal foot (if (= (cdr (assoc 0 (entget line))) "LINE") (cdr (assoc 11 (entget line))) (append (cdr (last (vl-remove-if-not '(lambda (x) (= (car x) 10)) (entget line)))) (list (cdr (assoc 38 (entget line)))))) 1e-7)) heading-feet)) heading-lines)))
(bht:block "HEAD_CUSTOM" '(((0 . "LINE") (8 . "0") (10 0.0 0.0 0.0) (11 2.0 0.0 0.0))))
(bht:obj-create "HEAD-CUSTOM" '(("nhom" . "BIEN_BAO") ("custom_block" . "HEAD_CUSTOM")) '("HEAD-1") T)
(bht:kh-free-apply "HEAD-CUSTOM" '(30.0 -5.0 0.0) 0.0 nil)
(bht:kh-heading-apply '("HEAD-CUSTOM") "FIXED" "" (/ pi 2.0))
(heading-check "custom-block-uses-native-X-head-convention" (heading-same-angle (heading-angle "HEAD-CUSTOM") (/ pi 2.0)))
(setq heading-arc (entmakex '((0 . "LWPOLYLINE") (100 . "AcDbEntity") (8 . "0") (100 . "AcDbPolyline") (90 . 2) (70 . 0) (10 0.0 0.0) (42 . 0.414213562373095) (10 10.0 10.0))))
(bht:route-create "HEAD-ARC" heading-arc "TIM_DUONG" 4.0 0.0 nil "QA")
(heading-check "bulged-PL-uses-local-arc-tangent" (heading-same-angle (bht:kh-route-heading (bht:obj-read "HEAD-A") "HEAD-ARC" '(8.485281374 1.514718626 0.0)) (- (/ pi 4.0))))
(princ (strcat "\nHEADING-FAIL=" (itoa heading-fails)))

;; Missing face uses the same +Y visible head as a regular sign.
(bht:obj-create "HEAD-MISSING" '(("nhom" . "BIEN_BAO") ("ma_hieu" . "W.207a") ("so_tru" . "1") ("tinh_trang" . "Mất mặt biển, còn trụ")) '("HEAD-1") T)
(bht:kh-free-apply "HEAD-MISSING" '(20.0 -6.0 0.0) 0.4 nil)
(setq missing-place (cdr (assoc 10 (entget (heading-insert "HEAD-MISSING")))))
(foreach hm '("ROUTE" "ROUTE_PERP")
 (bht:kh-heading-apply '("HEAD-MISSING" "HEAD-A") hm "HEAD-ROUTE" nil)
 (heading-check (strcat "missing-matches-sign-" hm) (heading-same-angle (heading-angle "HEAD-MISSING") (heading-angle "HEAD-A"))))
(foreach bearing '(0.0 0.7 1.5707963268 3.1415926536)
 (bht:kh-heading-apply '("HEAD-MISSING" "HEAD-A") "FIXED_PERP" "" bearing)
 (heading-check "missing-fixed-heading-matches-sign" (heading-same-angle (heading-angle "HEAD-MISSING") (heading-angle "HEAD-A"))))
(heading-check "missing-heading-preserves-insertion" (equal missing-place (cdr (assoc 10 (entget (heading-insert "HEAD-MISSING")))) 1e-8))
(setq missing-bn (cdr (assoc 2 (entget (heading-insert "HEAD-MISSING")))) missing-ent (entnext (tblobjname "BLOCK" missing-bn)) missing-solid nil)
(while (and missing-ent (/= (cdr (assoc 0 (entget missing-ent))) "ENDBLK"))
 (if (= (cdr (assoc 0 (entget missing-ent))) "SOLID") (setq missing-solid (entget missing-ent)))
 (setq missing-ent (entnext missing-ent)))
(heading-check "missing-has-blue-background" (= (cdr (assoc 420 missing-solid)) 30398))

;; Background follows the drawing fill switch; content and frame remain.
(setq missing-rec (bht:obj-read "HEAD-MISSING"))
(bht:meta-set "sign_fill_all" "0")
(setq missing-outline (bht:kh-block missing-rec) me (entnext (tblobjname "BLOCK" missing-outline)) ms 0 mt 0)
(while (and me (/= (cdr (assoc 0 (entget me))) "ENDBLK"))
 (if (and (= (cdr (assoc 0 (entget me))) "SOLID") (/= (cdr (assoc 60 (entget me))) 1)) (setq ms (1+ ms)))
 (if (= (cdr (assoc 0 (entget me))) "TEXT") (setq mt (1+ mt)))
 (setq me (entnext me)))
(heading-check "missing-outline-removes-background-keeps-text" (and (= ms 0) (= mt 1)))
(bht:meta-set "sign_fill_all" "1")
(heading-check "missing-fill-restores-original" (= (bht:kh-block missing-rec) missing-bn))
