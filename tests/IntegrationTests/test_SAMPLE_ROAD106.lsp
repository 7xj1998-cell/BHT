(setq sr106-points (bht:pt-all) sr106-records (bht:rec-all "OBJ") sr106-routes (bht:rec-all "ROUTE") sr106-chains (bht:rec-all "FIELD_CHAIN")
      sr106-angles (mapcar '(lambda (pr / d) (setq d (entget (cdr pr))) (list (car pr) (assoc 41 d) (assoc 42 d) (assoc 43 d) (assoc 50 d))) (bht:tagged-pairs "INSERT" "BHT_KH" 1)))
(setq sources nil)
(foreach pr (bht:tagged-pairs "INSERT" "BHT_KH" 1)
  (if (and (setq rec (bht:obj-read (car pr)))
           (member (bht:get rec "nhom") '("BIEN_BAO" "BANG_CHI_DAN" "BANG_QC" "KHAC" "CHUA_XAC_DINH" "DEN" "DEN_TH" "DEN_CS"))
           (setq pos (bht:obj-position rec sr106-points))) (setq sources (cons pos sources))))
(setq minx (apply 'min (mapcar 'car sources)) maxx (apply 'max (mapcar 'car sources))
      miny (apply 'min (mapcar 'cadr sources)) maxy (apply 'max (mapcar 'cadr sources)))
;; Explicitly a synthetic QA reference, not the surveyed centerline.
(if (> (- maxx minx) (- maxy miny))
  (setq start (list (- minx 100.0) (/ (+ miny maxy) 2.0)) finish (list (+ maxx 100.0) (cadr start)))
  (setq start (list (/ (+ minx maxx) 2.0) (- miny 100.0)) finish (list (car start) (+ maxy 100.0))))
(bht:layer "BHT_QA_THAM_CHIEU" 6)
(setq sr106-road (entmakex (list '(0 . "LWPOLYLINE") '(100 . "AcDbEntity") '(8 . "BHT_QA_THAM_CHIEU") '(100 . "AcDbPolyline") '(90 . 2) '(70 . 0) (cons 10 start) (cons 10 finish))))
(setq sr106-ms (getvar "MILLISECS") sr106-result (bht:api-run 'bht:kh-road-apply (list sr106-road "20" "20" "2" 1 "GAP_KHUC")))
(princ sr106-result)
(princ (strcat "\nSAMPLE-ROAD106 ms=" (itoa (- (getvar "MILLISECS") sr106-ms)) " eligible=" (itoa (length sources))))
(princ (if (and (= "OK" (car sr106-result)) (equal sr106-points (bht:pt-all))
  (equal sr106-angles (mapcar '(lambda (pr / d) (setq d (entget (cdr pr))) (list (car pr) (assoc 41 d) (assoc 42 d) (assoc 43 d) (assoc 50 d))) (bht:tagged-pairs "INSERT" "BHT_KH" 1)))) "\nSAMPLE-ROAD106-PRESERVE-PASS" "\nSAMPLE-ROAD106-PRESERVE-FAIL"))
(princ (if (and (equal sr106-routes (bht:rec-all "ROUTE")) (equal sr106-chains (bht:rec-all "FIELD_CHAIN"))
  (vl-every '(lambda (pair / before after) (setq before (cdr pair) after (bht:obj-read (car pair)))
    (vl-every '(lambda (key) (equal (bht:get before key) (bht:get after key))) '("ly_trinh_m" "ly_trinh_km" "route_id" "field_chain_id" "trang_thai_km" "phia_duong" "phia_tuyen"))) sr106-records)) "\nSAMPLE-ROAD106-CHAINAGE-PASS" "\nSAMPLE-ROAD106-CHAINAGE-FAIL"))
(setq sr106-count 0 sr106-bad 0)
(foreach pr (bht:tagged-pairs "INSERT" "BHT_KH" 1)
  (setq rec (bht:obj-read (car pr)))
  (if (and (equal (bht:get rec "kh_leader_mode") "GAP_KHUC")
           (not (equal (bht:get (cdr (assoc (car pr) sr106-records)) "kh_free_x") (bht:get rec "kh_free_x"))))
    (progn
      (setq sr106-count (1+ sr106-count) b (BHTDISPLAYBOUNDS (cons (cdr pr) (mapcar 'cdr (vl-remove-if-not '(lambda (p) (= (car p) (car pr))) (bht:tagged-pairs "TEXT" "BHT_KH" 1)))))
            source (bht:obj-position rec sr106-points) f (bht:kh-road-frame sr106-road source 1) side (if (> (nth 2 f) 0.0) 1 -1))
      (foreach corner (list (list (car b) (cadr b) 0.0) (list (car b) (nth 3 b) 0.0) (list (nth 2 b) (cadr b) 0.0) (list (nth 2 b) (nth 3 b) 0.0))
        (if (< (* side (nth 2 (bht:kh-road-frame sr106-road corner 1))) (- 22.0 1e-6)) (setq sr106-bad (1+ sr106-bad)))))))
(princ (strcat "\nSAMPLE-ROAD106 checked=" (itoa sr106-count) " overlaps=" (itoa sr106-bad)))
(princ (if (and (> sr106-count 100) (= sr106-bad 0)) "\nSAMPLE-ROAD106-CLEARANCE-PASS" "\nSAMPLE-ROAD106-CLEARANCE-FAIL"))
(princ)
