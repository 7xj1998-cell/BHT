(setq *cap1-fail* 0)
(defun cap1-check (name passed)
  (if (not passed) (setq *cap1-fail* (1+ *cap1-fail*)))
  (princ (strcat "\n" (if passed "PASS " "FAIL ") "CAP1 " name)))
(defun cap1-lines ()
  (mapcar 'cdr (vl-remove-if-not '(lambda (p) (= (car p) "CAP1-QA")) (append (bht:tagged-pairs "LINE" "BHT_KH" 1) (bht:tagged-pairs "LWPOLYLINE" "BHT_KH" 1)))))
(defun cap1-feet-world (insert / data feet transform)
  (setq data (entget insert) feet (BHTSIGNFEET (cdr (assoc 2 data)))
        transform (list (cdr (assoc 10 data)) (cdr (assoc 41 data)) (cdr (assoc 50 data))))
  (mapcar '(lambda (i) (bht:kh-foot-world (list (nth i feet) (nth (1+ i) feet) (nth (+ i 2) feet)) transform)) '(0 3)))
(defun cap1-leaders-correct (insert / ends)
  (setq ends (cap1-feet-world insert))
  (and (= (length (cap1-lines)) 2)
    (vl-every '(lambda (e) (vl-some '(lambda (xyz) (equal xyz (if (= (cdr (assoc 0 (entget e))) "LINE") (cdr (assoc 11 (entget e))) (append (cdr (last (vl-remove-if-not '(lambda (x) (= (car x) 10)) (entget e)))) (list (cdr (assoc 38 (entget e)))))) 1e-8)) ends)) (cap1-lines))))
(setq cap1-p1 (entmakex '((0 . "POINT") (10 180.0 40.0 0.0))) cap1-p2 (entmakex '((0 . "POINT") (10 184.0 42.0 0.0))))
(bht:pt-write-xdata cap1-p1 "CAP1-P1" "CAP1" "1" "Chân 1" 40.0 180.0 0.0 "BIEN_BAO" "test" "chân biển" "")
(bht:pt-write-xdata cap1-p2 "CAP1-P2" "CAP1" "2" "Chân 2" 42.0 184.0 0.0 "BIEN_BAO" "test" "chân biển" "")
(setq cap1-original-rtk (list (entget cap1-p1 '("BHT_PT")) (entget cap1-p2 '("BHT_PT"))) cap1-rec (bht:obj-read "CAP1-QA"))
(bht:obj-write "CAP1-QA" (bht:set-all cap1-rec "pt" '("CAP1-P1" "CAP1-P2")))
(cap1-check "portal-place" (= (cdr (assoc 'created (bht:kh-free-apply "CAP1-QA" '(190.0 48.0 0.0) 0.7 nil))) 1))
(setq cap1-insert (cdr (assoc "CAP1-QA" (bht:tagged-pairs "INSERT" "BHT_KH" 1))))
(cap1-check "portal-connects-two-rotated-feet" (cap1-leaders-correct cap1-insert))
(bht:kh-free-apply "CAP1-QA" '(195.0 50.0 0.0) 2.1 nil)
(cap1-check "move-rotate-retains-feet-connections" (cap1-leaders-correct cap1-insert))
(setq cap1-before (mapcar '(lambda (e) (entget e '("BHT_KH"))) (cap1-lines)))
(bht:symbol-sync '("CAP1-QA"))
(cap1-check "sync-idempotent" (equal cap1-before (mapcar '(lambda (e) (entget e '("BHT_KH"))) (cap1-lines))))
(cap1-check "content-persists" (= (bht:get (bht:obj-read "CAP1-QA") "sign_content") (bht:get cap1-rec "sign_content")))
(cap1-check "RTK-unchanged" (equal cap1-original-rtk (list (entget cap1-p1 '("BHT_PT")) (entget cap1-p2 '("BHT_PT")))))
(princ (strcat "\nCAP1-RTK-FAIL=" (itoa *cap1-fail*)))
(princ)
