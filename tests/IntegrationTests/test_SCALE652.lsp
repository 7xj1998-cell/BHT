(setq s652-fails 0)
(defun s652-check (n ok) (if (not ok) (setq s652-fails (1+ s652-fails))) (princ (strcat "\n" (if ok "PASS S652 " "FAIL S652 ") n)))
(setq sp (entmakex '((0 . "POINT") (10 100.0 100.0 0.0))))
(bht:pt-write-xdata sp "SCALE-PT" "QA" "1" "1" 100.0 100.0 0.0 "" "" "" "")
(setq survey-before (entget sp '("BHT_PT")) groups '("BIEN_BAO" "BANG_CHI_DAN" "BANG_QC" "KHAC" "CHUA_XAC_DINH") snapshots nil)
(bht:meta-set "sign_scale" "1")
(foreach group groups
  (bht:obj-create group (list (cons "nhom" group) '("ma_hieu" . "W.207a") '("mo_ta" . "ĐỊA PHẬN XÃ ĐỨC HÒA") (cons "so_tru" (if (= group "KHAC") "2" "1"))) '("SCALE-PT") T)
  (bht:symbol-sync (list group))
  (setq e (cdr (assoc group (bht:tagged-pairs "INSERT" "BHT_KH" 1))))
  ;; Include a manually positioned and rotated board.
  (if (= group "KHAC") (entmod (bht:dxf-put (bht:dxf-put (entget e) 10 '(120.0 95.0 0.0)) 50 1.50871342)))
  (setq snapshots (cons (list group (entget e) (bht:obj-read group)) snapshots)))
(foreach group '("COC_TIEU" "COT_KM")
  (bht:obj-create group (list (cons "nhom" group)) '("SCALE-PT") T)
  (bht:symbol-sync (list group)))
(setq other-before (mapcar '(lambda (id) (entget (cdr (assoc id (bht:tagged-pairs "INSERT" "BHT_KH" 1))))) '("COC_TIEU" "COT_KM")))
(s652-check "apply-global-three" (= (car (bht:api-sign-scale "3" "1")) "OK"))
(foreach saved snapshots
  (setq id (car saved) old (cadr saved) e (cdr (assoc id (bht:tagged-pairs "INSERT" "BHT_KH" 1))) d (entget e))
  (s652-check (strcat id "-same-uniform-scale") (and (equal (cdr (assoc 41 d)) 3.0 1e-8) (equal (cdr (assoc 42 d)) 3.0 1e-8) (equal (cdr (assoc 43 d)) 3.0 1e-8)))
  (s652-check (strcat id "-position-angle-kept") (and (equal (cdr (assoc 10 d)) (cdr (assoc 10 old)) 1e-8) (equal (cdr (assoc 50 d)) (cdr (assoc 50 old)) 1e-8)))
  (s652-check (strcat id "-record-kept") (equal (caddr saved) (bht:obj-read id))))
(setq scaled-before (mapcar '(lambda (id) (entget (cdr (assoc id (bht:tagged-pairs "INSERT" "BHT_KH" 1))))) groups))
(bht:api-sign-scale "3" "1")
(s652-check "idempotent" (equal scaled-before (mapcar '(lambda (id) (entget (cdr (assoc id (bht:tagged-pairs "INSERT" "BHT_KH" 1))))) groups)))
(s652-check "other-groups-unchanged" (equal other-before (mapcar '(lambda (id) (entget (cdr (assoc id (bht:tagged-pairs "INSERT" "BHT_KH" 1))))) '("COC_TIEU" "COT_KM"))))
(s652-check "survey-unchanged" (equal survey-before (entget sp '("BHT_PT"))))
(bht:obj-create "NEW" '(("nhom" . "KHAC") ("mo_ta" . "Bảng mới") ("so_tru" . "1")) '("SCALE-PT") T)
(bht:symbol-sync '("NEW"))
(s652-check "new-board-uses-three" (equal (cdr (assoc 41 (entget (cdr (assoc "NEW" (bht:tagged-pairs "INSERT" "BHT_KH" 1)))))) 3.0 1e-8))
(s652-check "board-offset-independent-of-size" (equal (bht:kh-auto-transform (bht:obj-read "NEW") '(100.0 100.0 0.0) 3.0) (bht:kh-route-transform (bht:obj-read "NEW") '(100.0 100.0 0.0) (bht:kh-scale)) 1e-8))
(princ (strcat "\nS652-FAIL=" (itoa s652-fails)))
