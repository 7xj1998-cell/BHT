(setq lr-fail 0 lr-n 0)
(defun lr-check (name ok)
  (setq lr-n (1+ lr-n)) (if (not ok) (setq lr-fail (1+ lr-fail)))
  (princ (strcat "\n" (if ok "PASS L126REAL " "FAIL L126REAL ") name)))
(defun lr-records () (mapcar '(lambda (id) (cons id (bht:obj-read id))) (bht:obj-ids)))
(defun lr-texts (/ pr d out)
  (foreach pr (bht:tagged-pairs "TEXT" "BHT_KH" 1)
    (setq d (entget (cdr pr)))
    (setq out (cons (list (cdr (assoc 5 d)) (bht:xget (cdr pr) "BHT_KH")
                    (cdr (assoc 1 d)) (cdr (assoc 11 d)) (cdr (assoc 40 d)) (cdr (assoc 50 d))) out)))
  (vl-sort out '(lambda (a b) (< (car a) (car b)))))
(defun lr-stable (value)
  (cond ((= (type value) 'REAL) (rtos value 2 8))
        ((listp value) (mapcar 'lr-stable value)) (T value)))
(defun lr-survey () (mapcar '(lambda (pr) (list (car pr) (entget (cdr pr) '("BHT_PT")))) (bht:tagged-pairs "POINT" "BHT_PT" 1)))
(if (= (getenv "BHT_LABEL126_PHASE") "REOPEN")
  (progn
    (setq f (open (getenv "BHT_LABEL126_SNAPSHOT") "r") saved (read (read-line f))) (close f)
    (lr-check "orientation-persisted" (= (bht:meta "sign_label_orientation" "") "PERPENDICULAR"))
    (lr-check "records-persisted" (equal (car saved) (lr-records)))
    (lr-check "caption-geometry-persisted" (equal (cadr saved) (lr-stable (lr-texts))))
    (lr-check "survey-persisted" (equal (caddr saved) (lr-stable (mapcar '(lambda (p) (list (car p) (cdr (assoc 10 (cadr p))))) (lr-survey))))))
  (progn
    (setq before (lr-records) survey (lr-survey))
    (lr-check "real-drawing-has-records" (> (length before) 100))
    (lr-check "parallel-scale3-applied" (= (car (bht:api-sign-display "3" "3" "PARALLEL")) "OK"))
    (lr-check "parallel-preserves-all-records" (equal before (lr-records)))
    (foreach old before
      (if (not (equal (cdr old) (bht:obj-read (car old))))
        (progn (princ (strcat "\nL126REAL-DIFF " (car old)))
          (foreach field (bht:obj-read (car old))
            (if (not (member field (cdr old))) (prin1 field))))))
    (lr-check "perpendicular-scale3-applied" (= (car (bht:api-sign-display "3" "3" "PERPENDICULAR")) "OK"))
    (lr-check "perpendicular-preserves-all-records" (equal before (lr-records)))
    (lr-check "all-survey-entities-preserved" (equal survey (lr-survey)))
    (setq texts (lr-texts))
    (bht:api-sign-display "3" "3" "PERPENDICULAR")
    (lr-check "real-refresh-idempotent" (equal texts (lr-texts) 1e-8))
    (setq f (open (getenv "BHT_LABEL126_SNAPSHOT") "w"))
    (prin1 (list before (lr-stable texts) (lr-stable (mapcar '(lambda (p) (list (car p) (cdr (assoc 10 (cadr p))))) survey))) f) (close f)))
(princ (strcat "\nL126REAL-CHECKS=" (itoa lr-n) " FAIL=" (itoa lr-fail)))
