(setq qa110-fails 0)
(defun qa110-check (name ok)
  (if (not ok) (setq qa110-fails (1+ qa110-fails)))
  (princ (strcat "\n" (if qa110-baseline "BASELINE " (if ok "PASS " "FAIL ")) "QA110 " name "=" (if ok "OK" "FAILED"))))
(princ (strcat "\nQA110-ROUTES=" (vl-prin1-to-string (bht:route-ids))))
(setq qa110-points (bht:pt-all) qa110-records (bht:rec-all "OBJ") qa110-routes (bht:rec-all "ROUTE"))
(setq qa110-route (bht:route-read "DOAN_13"))
(if (null qa110-route) (setq qa110-route (cdar qa110-routes)))
(setq qa110-ent (bht:route-ent qa110-route))
(defun qa110-cad () (mapcar '(lambda (p) (entget (cdr p) '("*"))) (append (bht:tagged-pairs "*" "BHT_KH" 1) (bht:tagged-pairs "*" "BHT_SIGN_ORIGIN" 1))))
(setq qa110-cad-before (qa110-cad))
(defun qa110-unrelated ()
  (mapcar '(lambda (p) (entget (cdr p) '("*")))
    ;; D13 contains three signs and three station markers in this fixture.
    (vl-remove-if '(lambda (p) (member (car p) '("OBJ-000087" "OBJ-000088" "OBJ-000089" "OBJ-000090" "OBJ-000098" "OBJ-000175")))
      (append (bht:tagged-pairs "*" "BHT_KH" 1) (bht:tagged-pairs "*" "BHT_SIGN_ORIGIN" 1)))))
(setq qa110-unrelated-before (qa110-unrelated))
(setq qa110-tagged bht:tagged-pairs qa110-scans 0 qa110-refresh bht:kh-layout-refresh qa110-passes 0)
(defun bht:tagged-pairs (kind app n) (setq qa110-scans (1+ qa110-scans)) (qa110-tagged kind app n))
(defun bht:kh-layout-refresh (ids) (setq qa110-passes (1+ qa110-passes)) (qa110-refresh ids))
(setq qa110-target bht:kh-road-target)
(defun bht:kh-road-target (oid rec index e labels source base / result)
  (setq result (qa110-target oid rec index e labels source base))
  (if (and result (> qa110-passes 0) (> (distance result base) 0.000001))
    (princ (strcat "\nQA110-STEP " oid " pass=" (itoa qa110-passes) " delta=" (rtos (distance result base) 2 8))))
  result)
(setq qa110-start (getvar "MILLISECS"))
(setq qa110-result (if (= (bht:get qa110-route "route_id") "DOAN_13")
  (bht:api-run 'bht:kh-center-apply (list "DOAN_13" "10" "GAP_KHUC"))
  (bht:api-run 'bht:kh-road-apply (list qa110-ent "5" "5" "2" 1 "GAP_KHUC"))))
(princ (strcat "\nQA110-BULK-MS=" (itoa (- (getvar "MILLISECS") qa110-start)) " SCANS=" (itoa qa110-scans) " REFRESH=" (itoa qa110-passes)))
(princ (strcat "\nQA110-RESULT=" (vl-prin1-to-string (list (car qa110-result) (cadr qa110-result)))))
(qa110-check "bulk-success" (= (car qa110-result) "OK"))
(qa110-check "survey-unchanged" (and (equal qa110-points (bht:pt-all)) (equal qa110-routes (bht:rec-all "ROUTE"))
  (vl-every '(lambda (pair / after) (setq after (bht:obj-read (car pair)))
    (vl-every '(lambda (key) (equal (bht:get (cdr pair) key) (bht:get after key)))
      '("ly_trinh_m" "ly_trinh_km" "route_id" "doan" "goi" "ma_hieu" "phia_duong" "progress_locked" "revision_id"))) qa110-records)))
(setq bht:tagged-pairs qa110-tagged bht:kh-layout-refresh qa110-refresh bht:kh-road-target qa110-target)
(if (not qa110-baseline)
  (progn
    (if (= (bht:get qa110-route "route_id") "DOAN_13")
      (progn
        (qa110-check "fixture-six-objects-belong-to-d13" (vl-every '(lambda (id) (= (bht:get (bht:obj-read id) "route_id") "DOAN_13"))
          '("OBJ-000087" "OBJ-000088" "OBJ-000089" "OBJ-000090" "OBJ-000098" "OBJ-000175")))
        (qa110-check "unrelated-symbols-and-markers-unchanged" (equal qa110-unrelated-before (qa110-unrelated)))
        (foreach qa110-old qa110-unrelated-before
          (setq qa110-new (entget (cdr (assoc -1 qa110-old)) '("*")))
          (if (not (equal qa110-old qa110-new))
            (princ (strcat "\nQA110-UNRELATED-DIFF " (cdr (assoc 5 qa110-old)) " BEFORE=" (vl-prin1-to-string qa110-old) " AFTER=" (vl-prin1-to-string qa110-new)))))
        (foreach qa110-id '("OBJ-000087" "OBJ-000088" "OBJ-000090")
          (setq qa110-e (cdr (assoc qa110-id (bht:tagged-pairs "INSERT" "BHT_KH" 1)))
                qa110-labels (mapcar 'cdr (vl-remove-if-not '(lambda (p) (= (car p) qa110-id)) (bht:tagged-pairs "TEXT" "BHT_KH" 1)))
                qa110-bounds (BHTDISPLAYBOUNDS (cons qa110-e qa110-labels))
                qa110-center (list (/ (+ (car qa110-bounds) (nth 2 qa110-bounds)) 2.0) (/ (+ (cadr qa110-bounds) (nth 3 qa110-bounds)) 2.0) 0.0)
                qa110-radius (/ (distance (list (car qa110-bounds) (cadr qa110-bounds)) (list (nth 2 qa110-bounds) (nth 3 qa110-bounds))) 2.0))
          (qa110-check (strcat "independent-10m-clearance-" qa110-id)
            (>= (- (distance qa110-center (vlax-curve-getClosestPointTo qa110-ent qa110-center)) qa110-radius) (- 10.0 1e-6))))))
    (setq qa110-cad-after (qa110-cad))
    (setq qa110-result (if (= (bht:get qa110-route "route_id") "DOAN_13")
      (bht:api-run 'bht:kh-center-apply (list "DOAN_13" "10" "GAP_KHUC"))
      (bht:api-run 'bht:kh-road-apply (list qa110-ent "5" "5" "2" 1 "GAP_KHUC"))))
    (qa110-check "repeat-layout-no-movement-or-duplicates" (equal qa110-cad-after (qa110-cad) 1e-7))
    (setq qa110-record-after (bht:rec-all "OBJ") qa110-meta-after (bht:rec-all "META") qa110-cad-after (qa110-cad))
    (defun qa110-fault ()
      (bht:meta-set "qa110-fault" "changed")
      (setq qa110-fault-e (cdr (car (bht:tagged-pairs "INSERT" "BHT_KH" 1))))
      (entmod (bht:dxf-put (entget qa110-fault-e) 10 '(0.0 0.0 0.0)))
      (bht:display-fail "QA110 injected error after CAD write"))
    (setq qa110-result (bht:kh-display-transaction 'qa110-fault nil))
    (qa110-check "fault-rollback-canonical-records-meta-cad" (and (eq (car qa110-result) 'LOI)
      (equal qa110-cad-after (qa110-cad)) (equal qa110-record-after (bht:rec-all "OBJ")) (equal qa110-meta-after (bht:rec-all "META"))))
    (qa110-check "fault-reason-visible" (wcmatch (cadr qa110-result) "*QA110 injected*"))
    (load (strcat (getenv "BHT_QA110_TESTS") "/state110.lsp"))
    (setq qa110-file (open (strcat (getvar "DWGPREFIX") "qa110-saved-state.lsp") "w"))
    (prin1 (qa110-saved-state) qa110-file) (close qa110-file)
    (command-s "_.QSAVE")))
(princ (strcat "\nQA110-DONE FAIL=" (itoa qa110-fails)))
(princ)
