;;; BHT 0.3.3 - phien R (dung lai nguyen kich ban hoi quy cua 0.3.2): HOI QUY chuc nang 0.2.0/0.3.1 (dung lai kich ban test_A cua 0.2.0,
;;; chi doi duong dan nap Lisp, phien ban va thu muc xuat). Ban ve: BAN SAO sample-route.dwg.
(load "C:/Users/Le Bao/BHT_TEST_V044/t_common.lsp")
(tbegin "R")
(setq e (tload))
(tchk "A01" "nạp BHT 1.1.5 từ đường dẫn có dấu" (and (null e) (= *bht-version* "1.1.5")) (if e e *bht-version*))
;; A02
(setq r (tsafe "A02" "selftest" '(lambda () (bht:selftest))))
(if r (tchk "A02" "BHTTEST hàm thuần" (= (cadr r) 0) (strcat (itoa (car r)) " pass, " (itoa (cadr r)) " fail")))
;; A03-A06 nhap
(setq r (tsafe "A03" "nhập CSV" '(lambda () (bht:import-csv (strcat *T-DIR* "data/survey.csv") "BOT19"))))
(if r (tchk "A03" "nhập 526 điểm lần đầu" (and (= (rv r 'added) 526) (= (rv r 'invalid) 0) (= (rv r 'conflict) 0)) r))
(setq r (tsafe "A04" "nhập lại" '(lambda () (bht:import-csv (strcat *T-DIR* "data/survey.csv") "BOT19"))))
(if r (tchk "A04" "nhập lại cùng dataset không tạo trùng" (and (= (rv r 'added) 0) (= (rv r 'same) 526)) r))
(setq r (tsafe "A05" "nhập dataset khác" '(lambda () (bht:import-csv (strcat *T-DIR* "data/survey.csv") "XX"))))
(if r (tchk "A05" "cùng CSV dưới dataset khác bị chặn (trùng nội dung)" (and (= (rv r 'added) 0) (= (rv r 'dupcontent) 526)) r))
(setq r (tsafe "A06" "nhập CSV sửa 1 dòng" '(lambda () (bht:import-csv (strcat *T-DIR* "data/survey_mod.csv") "BOT19"))))
(if r (tchk "A06" "dòng thay đổi = xung đột, không ghi đè" (and (= (rv r 'conflict) 1) (= (rv r 'same) 525) (= (rv r 'added) 0)) r))
;; A07
(setq idx (bht:pt-all) p1 (bht:pt-find "BOT19-R-000001" idx) p5 (bht:pt-find "BOT19-R-000005" idx))
(tchk "A07" "526 điểm, X=Đông Y=Bắc Z, ID theo dòng"
      (and (= (length idx) 526) p1 (equal (bht:pv p1 'xyz) '(575301.489 1187855.825 1.292) 1e-9)
           (= (bht:pv p1 'name) "Ranhdat") (= (bht:pv p5 'z) "2.305") (= (bht:pv p5 'desc) "1"))
      (strcat (itoa (length idx)) " điểm; P1 XYZ=" (vl-princ-to-string (bht:pv p1 'xyz)) "; P5 Z=" (bht:pv p5 'z)))
;; A08 verbatim toan bo
(setq recs (car (bht:csv-records (strcat *T-DIR* "data/survey.csv") "BOT19")) bad 0)
(foreach rr recs
  (setq p (bht:pt-find (car rr) idx))
  (if (not (and p (= (bht:pv p 'name) (nth 3 rr)) (= (bht:pv p 'n) (nth 4 rr)) (= (bht:pv p 'e) (nth 5 rr))
                (= (bht:pv p 'z) (nth 6 rr)) (= (bht:pv p 'desc) (nth 7 rr))
                (equal (bht:pv p 'xyz) (list (atof (nth 5 rr)) (atof (nth 4 rr)) (atof (nth 6 rr))) 1e-9)))
    (setq bad (1+ bad))))
(tchk "A08" "526/526 điểm giữ nguyên chuỗi gốc + tọa độ" (= bad 0) (strcat "sai lệch " (itoa bad)))
;; A09 diem v0.1 + unicode
(bht:regapp "BHT_RTK") (bht:regapp "BHT_ASSET") (bht:regapp "BHT_PHOTO")
(setq leg1 (entmakex '((0 . "POINT") (8 . "BHT_RTK") (10 575100.0 1180100.0 1.5))))
(bht:xset leg1 "BHT_RTK" '("VN1" "bien cam cu"))
(bht:xset leg1 "BHT_ASSET" '("SIGN-001" "sign" "207e" "PKG-01" "KM39"))
(bht:xset leg1 "BHT_PHOTO" '("D:/photos/sign-001.jpg"))
(setq leg2 (entmakex '((0 . "POINT") (8 . "BHT_RTK") (10 575110.0 1180110.0 1.0))))
(bht:xset leg2 "BHT_RTK" '("LEG2" "coctiu cu"))
(setq r (tsafe "A09" "nhập vn.csv" '(lambda () (bht:import-csv (strcat *T-DIR* "data/vn.csv") "VN"))))
(setq idx (bht:pt-all) f (open (strcat *T-DIR* "data/long_desc.txt") "r") longd (read-line f))
(close f)
(if r (tchk "A09" "tiếng Việt/dấu phẩy/ngoặc kép/mô tả dài/dòng lỗi/nhận điểm v0.1"
            (and (= (rv r 'added) 2) (= (rv r 'adopted) 1) (= (rv r 'invalid) 1)
                 (= (bht:pv (bht:pt-find "VN-R-000001" idx) 'desc) "biển \"cấm\", đỗ xe")
                 (= (bht:pv (bht:pt-find "VN-R-000004" idx) 'desc) "bb.cn,phan,lan")
                 (= (bht:pv (bht:pt-find "VN-R-000005" idx) 'desc) longd)
                 (equal leg1 (bht:pv (bht:pt-find "VN-R-000001" idx) 'ent)))
            (strcat (vl-princ-to-string r) " | VN1 desc=[" (bht:pv (bht:pt-find "VN-R-000001" idx) 'desc) "] len VN5="
                    (itoa (strlen (bht:pv (bht:pt-find "VN-R-000005" idx) 'desc))) " VN4=[" (vl-princ-to-string (bht:pv (bht:pt-find "VN-R-000004" idx) 'desc)) "] ent1=" (vl-princ-to-string (bht:pv (bht:pt-find "VN-R-000001" idx) 'ent)) " leg1=" (vl-princ-to-string leg1) " eqlong=" (vl-princ-to-string (= (bht:pv (bht:pt-find "VN-R-000005" idx) 'desc) longd)))))
;; A10 nang cap
(setq r (tsafe "A10" "BHTNANGCAP" '(lambda () (bht:migrate-v01))))
(setq o (bht:obj-read "SIGN-001"))
(if r (tchk "A10" "nâng cấp v0.1: gán ID điểm cũ + tạo hồ sơ từ BHT_ASSET"
            (and (= (car r) 1) (= (cadr r) 1) o (equal (bht:get-all o "pt") '("VN-R-000001"))
                 (equal (bht:get-all o "anh_file") '("D:/photos/sign-001.jpg")))
            (strcat (vl-princ-to-string r) " pt=" (vl-princ-to-string (bht:get-all o "pt")))))
;; A11 doi tuong
(setq r1 (bht:obj-create "OBJ-BANG" '(("nhom" . "4") ("so_tru" . "2") ("so_mat" . "1") ("mo_ta" . "bảng 2 chân"))
                         '("BOT19-R-000035" "BOT19-R-000036") nil))
(setq r2 (bht:obj-create "OBJ-COT" '(("nhom" . "BIEN_BAO") ("so_tru" . "1") ("so_mat" . "2") ("mat" . "TEST-1") ("mat" . "TEST-2"))
                         '("BOT19-R-000151") nil))
(setq r3 (bht:obj-create "OBJ-BANG" '(("nhom" . "1")) '("BOT19-R-000010") nil))
(setq r4 (bht:obj-create "OBJ-X" '(("nhom" . "1")) '("BOT19-R-000035") nil))
(setq r5 (bht:obj-create "OBJ-Y" '(("nhom" . "1")) '("KHONG-CO") nil))
(setq o (bht:obj-read "OBJ-COT"))
(tchk "A11" "hồ sơ đối tượng: nhiều điểm, số trụ/mặt tách riêng, chặn trùng ID/điểm/thiếu điểm"
      (and (car r1) (car r2) (not (car r3)) (not (car r4)) (not (car r5))
           (= (bht:get (bht:obj-read "OBJ-BANG") "so_tru") "2") (= (length (bht:get-all (bht:obj-read "OBJ-BANG") "pt")) 2)
           (equal (bht:get-all o "mat") '("TEST-1" "TEST-2")) (= (bht:get o "nhom") "BIEN_BAO"))
      (strcat (cadr r3) " / " (cadr r4) " / " (cadr r5)))
;; A12 anh
(setq r (tsafe "A12" "nhập BHT_PHOTO.tsv" '(lambda () (bht:photo-import-tsv (strcat *T-DIR* "data/BHT_PHOTO.tsv") T))))
(setq r2 (bht:photo-import-tsv (strcat *T-DIR* "data/BHT_PHOTO.tsv") T))
(setq ph1 (bht:photo-read "BOT19-P-000001") ph204 (bht:photo-read "BOT19-P-000204"))
(setq ss (ssget "_X" '((0 . "INSERT") (-3 ("BHT_ANHPT")))))
(if r (tchk "A12" "205 ảnh (203 GPS + 2 ảnh 0,0 được giữ), nhập lại không trùng, vị trí chụp"
            (and (= (rv r 'added) 205) (= (rv r 'validgps) 203) (= (rv r 'invalidgps) 2) (= (rv r2 'added) 0)
                 (= (rv r2 'same) 205) ph204 (= (bht:get ph204 "gps_hop_le") "0")
                 (equal (atof (bht:get ph1 "e")) 575081.764 0.002) (equal (atof (bht:get ph1 "n")) 1189223.379 0.002)
                 ss (= (sslength ss) 203))
            (strcat (vl-princ-to-string r) " | P1 E,N=" (bht:get ph1 "e") "," (bht:get ph1 "n")
                    " | ký hiệu=" (if ss (itoa (sslength ss)) "0"))))
;; A13 de xuat
(setq r (tsafe "A13" "đề xuất ghép" '(lambda () (bht:photo-suggest 10.0 2.0))))
(setq linked 0)
(foreach oid (bht:obj-ids) (setq linked (+ linked (length (bht:get-all (bht:obj-read oid) "anh")))))
(setq conf 0)
(foreach pid (bht:rec-keys "PHOTO") (if (= (bht:get (bht:photo-read pid) "trang_thai") "DA_XAC_NHAN") (setq conf (1+ conf))))
(if r (tchk "A13" "ghép ảnh chỉ tạo đề xuất, không tự liên kết"
            (and (= linked 0) (= conf 0) (= (+ (rv r 'suggested) (rv r 'ambiguous) (rv r 'none)) 203) (= (rv r 'skipped) 2))
            (vl-princ-to-string r)))
;; A14 gan tay anh 0,0
(setq r1 (bht:photo-link "BOT19-P-000204" "OBJ-COT" "THU_CONG") r2 (bht:photo-link "BOT19-P-000205" "KHONG-CO" "THU_CONG"))
(tchk "A14" "gắn tay ảnh GPS 0,0; hai chiều đồng bộ; từ chối đối tượng không có"
      (and (car r1) (not (car r2)) (member "OBJ-COT" (bht:get-all (bht:photo-read "BOT19-P-000204") "doi_tuong"))
           (= (car (bht:split (car (bht:get-all (bht:obj-read "OBJ-COT") "anh")) "|")) "BOT19-P-000204"))
      (cadr r2))
;; A15 chap nhan de xuat P:
(setq cand nil)
(foreach pid (bht:rec-keys "PHOTO")
  (setq pr (bht:photo-read pid))
  (if (and (null cand) (= (bht:get pr "trang_thai") "DE_XUAT") (bht:starts (car (bht:get-all pr "de_xuat")) "P:"))
    (setq cand pid)))
(setq nobj (length (bht:obj-ids)))
(if cand
  (progn
    (setq pr (bht:photo-read cand) tgt (car (bht:split (car (bht:get-all pr "de_xuat")) "|"))
          r (bht:accept-target cand tgt))
    (tchk "A15" "duyệt đề xuất điểm lẻ -> tạo đối tượng mới + liên kết" (and (car r) (= (length (bht:obj-ids)) (1+ nobj))
          (= (bht:get (bht:photo-read cand) "trang_thai") "DA_XAC_NHAN")) (strcat cand " -> " tgt)))
  (tchk "A15" "duyệt đề xuất" nil "không có đề xuất P: nào"))
;; A16 tuyen
(bht:import-csv (strcat *T-DIR* "data/rt.csv") "RT")
(setq pl (entmakex '((0 . "LWPOLYLINE") (100 . "AcDbEntity") (8 . "0") (100 . "AcDbPolyline") (90 . 2) (70 . 0)
                     (10 575000.0 1180000.0) (10 576500.0 1180000.0))))
(setq ln (entmakex '((0 . "LINE") (8 . "0") (10 0.0 0.0 0.0) (11 1.0 0.0 0.0))))
(setq pss (ssget "_X" '((0 . "ACAD_PROXY_ENTITY"))))
(setq pchk (if pss (bht:route-check-ent (ssname pss 0)) '(nil "không có proxy trong DWG")))
(setq lchk (bht:route-check-ent ln))
(entdel ln)
(setq rc (bht:route-create "TUYEN1" pl "TIM_DUONG" 100.0 0.0 nil "test"))
(setq s0 (bht:station-route (bht:route-read "TUYEN1") '(575250.0 1180010.0 1.0)))
(bht:route-add-mark "TUYEN1" 0.0 39000.0 39000.0 "test" "")
(bht:route-add-mark "TUYEN1" 500.0 39500.0 39600.0 "test gãy" "")
(bht:route-add-mark "TUYEN1" 1000.0 40100.0 40100.0 "test" "")
(setq dupm (bht:route-add-mark "TUYEN1" 500.0 1.0 1.0 "dup" ""))
(setq rr (bht:route-read "TUYEN1"))
(setq s1 (bht:station-route rr '(575250.0 1180010.0 1.0)) s2 (bht:station-route rr '(575750.0 1179995.0 1.0))
      s3 (bht:station-route rr '(576200.0 1180000.0 1.0)) s4 (bht:station-route rr '(575300.0 1180250.0 1.0)))
(tchk "A16a" "từ chối proxy TDT làm tuyến" (and pss (not (car pchk))) (strcat (if pss (itoa (sslength pss)) "0") " proxy; " (cadr pchk)))
(tchk "A16b" "từ chối LINE; nhận LWPOLYLINE" (and (not (car lchk)) (car rc)) (cadr lchk))
(tchk "A16c" "tuyến chưa có mốc -> Km chưa xác định" (= (rv s0 'status) "CHUA_CO_MOC") (rv s0 'status))
(tchk "A16d" "nội suy giữa mốc + phía trái" (and (= (rv s1 'status) "NOI_SUY") (equal (rv s1 'station) 39250.0 1e-6)
       (equal (rv s1 'offset) 10.0 1e-6) (= (rv s1 'side) "TRAI")) (vl-princ-to-string s1))
(tchk "A16e" "không nội suy xuyên điểm gãy Km + phía phải" (and (equal (rv s2 'station) 39850.0 1e-6) (= (rv s2 'side) "PHAI"))
      (vl-princ-to-string s2))
(tchk "A16f" "ngoài phạm vi mốc -> chưa xác định; xa tuyến -> XA_TUYEN"
      (and (= (rv s3 'status) "CHUA_XAC_DINH") (null (rv s3 'station)) (= (rv s4 'status) "XA_TUYEN"))
      (strcat (rv s3 'status) " / " (rv s4 'status)))
(tchk "A16g" "chặn 2 mốc cùng vị trí" (not (car dupm)) (cadr dupm))
;; A17 doi tuong RT + ly trinh
(bht:obj-create "OBJ-RT1" '(("nhom" . "1")) '("RT-R-000001") nil)
(bht:obj-create "OBJ-RT2" '(("nhom" . "2")) '("RT-R-000002") nil)
(bht:obj-create "OBJ-RT3" '(("nhom" . "3")) '("RT-R-000003") nil)
(setq r (bht:station-objects))
(setq o1 (bht:obj-read "OBJ-RT1") o3 (bht:obj-read "OBJ-RT3") ob (bht:obj-read "OBJ-BANG"))
(tchk "A17" "lưu lý trình/offset/nguồn Km vào hồ sơ đối tượng"
      (and (= (bht:get o1 "ly_trinh_m") "39250.000") (= (bht:get o1 "ly_trinh_km") "Km39+250.00") (= (bht:get o1 "phia_tuyen") "TRAI")
           (= (bht:get o1 "route_id") "TUYEN1") (/= (bht:get o1 "nguon_km") "")
           (= (bht:get o3 "ly_trinh_m") "") (= (bht:get o3 "trang_thai_km") "CHUA_XAC_DINH")
           (= (bht:get ob "trang_thai_km") "XA_TUYEN"))
      (strcat (vl-princ-to-string r) " | RT1 " (bht:get o1 "ly_trinh_km") " " (bht:get o1 "nguon_km")))
;; A18 goi thau
(setq n (bht:seg-load (strcat *T-DIR* "data/BHT_GOI_THAU.tsv") T))
(setq sg (bht:rec-read "SEG" "DOAN02"))
(tchk "A18" "nạp 15 đoạn / 3 gói từ bảng xlsx" (and (= n 15) (= (bht:get sg "package_id") "GT1") (= (bht:get sg "side") "TRAI")
      (= (bht:get sg "km_start_m") "39000")) (strcat (itoa n) " đoạn; DOAN02=" (bht:get sg "package_name")))
;; A19 phan doan
(setq r (bht:assign-segments))
(setq o1 (bht:obj-read "OBJ-RT1") o2 (bht:obj-read "OBJ-RT2") o3 (bht:obj-read "OBJ-RT3"))
(setq okA (and (= (bht:get o1 "doan") "DOAN02") (= (bht:get o1 "goi") "GT1") (= (bht:get o1 "gan_doan_pp") "TU_DONG")
               (= (bht:get o2 "doan") "DOAN12") (= (bht:get o3 "gan_doan_pp") "CHUA_XAC_DINH_KM")))
(setq rr (bht:route-read "TUYEN1"))
(bht:route-write "TUYEN1" (bht:set rr "loai" "TIM_RANH"))
(bht:station-objects)
(bht:assign-segments)
(setq o1b (bht:obj-read "OBJ-RT1"))
(setq okB (and (= (bht:get o1b "gan_doan_pp") "NHIEU_DOAN") (= (bht:get o1b "doan_ung_vien") "DOAN02;DOAN12") (= (bht:get o1b "doan") "")))
(bht:assign-manual "OBJ-RT1" "DOAN02")
(bht:assign-segments)
(setq o1c (bht:obj-read "OBJ-RT1"))
(setq okC (and (= (bht:get o1c "gan_doan_pp") "THU_CONG") (= (bht:get o1c "doan") "DOAN02") (= (bht:get o1c "goi") "GT1")))
(tchk "A19" "phân đoạn theo Km+phía; chồng lấn -> NHIEU_DOAN; gán tay được giữ" (and okA okB okC)
      (strcat "A=" (vl-princ-to-string okA) " B=" (vl-princ-to-string okB) " C=" (vl-princ-to-string okC) " " (vl-princ-to-string r)))
;; A20 ky hieu
(setq n1 (bht:symbols-draw 1.0 1.5) n2 (bht:symbols-draw 1.0 1.5))
(setq ss (ssget "_X" '((0 . "INSERT") (-3 ("BHT_KH")))))
(tchk "A20" "vẽ ký hiệu, vẽ lại không nhân đôi" (and (= n1 n2) ss (= (sslength ss) n2) (= n2 (length (bht:obj-ids))))
      (strcat "đối tượng=" (itoa (length (bht:obj-ids))) " ký hiệu=" (if ss (itoa (sslength ss)) "0")))
;; A21 xuat
(vl-mkdir (strcat *T-DIR* "run/out_R"))
(setq r (tsafe "A21" "xuất CSV" '(lambda () (bht:export-all (strcat *T-DIR* "run/out_R") "BHT_"))))
(if r (tchk "A21" "xuất 4 file CSV; tổng hợp đếm mỗi đối tượng 1 lần"
            (and (= (rv r 'points) 534) (= (rv r 'objects) (length (bht:obj-ids))) (= (rv r 'photos) 205)
                 (= (rv r 'total-objects) (length (bht:obj-ids))))
            (vl-princ-to-string r)))
(setq first (car (bht:read-lines (strcat *T-DIR* "run/out_R/BHT_DIEM_RTK.csv"))))
(tchk "A21a" "CSV dùng tiêu đề tiếng Việt có dấu"
      (and first (vl-string-search "ID điểm khảo sát" first) (vl-string-search "Tên điểm" first)
           (vl-string-search "Lý trình Km" first) (vl-string-search "Tệp nguồn" first)) first)
;; A22 kiem tra
(setq k1 (bht:check))
(setq e (bht:pv (bht:pt-find "BOT19-R-000002" (bht:pt-all)) 'ent) d (entget e) old (assoc 10 d))
(entmod (subst (list 10 (+ (cadr old) 0.5) (caddr old) (cadddr old)) old d))
(setq k2 (bht:check))
(entmod (subst old (assoc 10 (entget e)) (entget e)))
(setq k3 (bht:check))
(tchk "A22" "BHTKT: 0 lỗi; phát hiện điểm bị dịch; hết lỗi khi trả lại" (and (= (car k1) 0) (= (car k2) 1) (= (car k3) 0))
      (strcat "lỗi " (itoa (car k1)) "/" (itoa (car k2)) "/" (itoa (car k3)) ", cảnh báo " (itoa (cadr k1))))
(foreach l (caddr k1) (tlog (strcat "   KT: " l)))
;; A23 lenh
(setq bad nil)
(foreach c '(c:BHTTRANGTHAI c:BHTTEST c:BHTKT c:BHTLYTRINH)
  (if (vl-catch-all-error-p (vl-catch-all-apply c nil)) (setq bad (cons c bad))))
(tchk "A23" "chạy lệnh không tương tác BHTTRANGTHAI/BHTTEST/BHTKT/BHTLYTRINH" (null bad) (vl-princ-to-string bad))
(tend "R")
(princ)
