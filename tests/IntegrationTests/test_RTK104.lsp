(vl-load-com)
(setq qa-fails 0 qa-checks 0)
(defun r104-check (name ok)
 (setq qa-checks (1+ qa-checks)) (if (not ok) (setq qa-fails (1+ qa-fails)))
 (princ (strcat "\n" (if ok "PASS RTK104 " "FAIL RTK104 ") name)))
(defun r104-labels () (mapcar 'cdr (bht:tagged-pairs "TEXT" "BHT_NHAN" 1)))
(defun r104-snapshot () (mapcar '(lambda (e) (entget e '("*"))) (r104-labels)))
(defun r104-angle-p (a) (vl-every '(lambda (e) (equal (cdr (assoc 50 (entget e))) a 1e-8)) (r104-labels)))
(r104-check "empty-drawing-safe" (= (car (bht:api-label-rotate "UCS")) "OK"))
(foreach row '(("QA-A" 100.0 200.0) ("QA-B" 120.0 220.0))
 (setq p (entmakex (list '(0 . "POINT") (cons 10 (list (cadr row) (caddr row) 0.0)))))
 (bht:pt-write-xdata p (car row) "QA" "1" (car row) (caddr row) (cadr row) 0.0 "RTK" "QA" "Nhãn thử" ""))
(bht:meta-set "nhan_id" "1") (bht:lbl-sync)
(setq qa-points (bht:pt-all) qa-labels (r104-labels) qa-before (r104-snapshot))
(setq qa-other (entmakex '((0 . "TEXT") (10 30.0 20.0 0.0) (40 . 1.0) (1 . "OTHER") (50 . 0.37))))
(setq qa-other-before (entget qa-other))
(r104-check "all-four-label-kinds-created" (= (length qa-labels) 8))
(command "_.UCS" "_World") (command "_.UCS" "_Z" "30")
(setq qa-ucs (getvar "UCSXDIR"))
(r104-check "UCS-api" (= (car (bht:api-label-rotate "UCS")) "OK"))
(r104-check "angle-follows-rotated-UCS" (r104-angle-p (/ pi 6.0)))
(r104-check "UCS-unchanged" (equal qa-ucs (getvar "UCSXDIR")))
(r104-check "points-unchanged" (equal qa-points (bht:pt-all)))
(r104-check "foreign-text-unchanged" (equal qa-other-before (entget qa-other)))
(r104-check "content-height-style-unchanged"
 (equal (mapcar '(lambda (d) (list (assoc 1 d) (assoc 40 d) (assoc 7 d))) qa-before)
        (mapcar '(lambda (d) (list (assoc 1 d) (assoc 40 d) (assoc 7 d))) (r104-snapshot))))
(r104-check "labels-pinned" (vl-every '(lambda (e) (= (bht:lbl-state e) 'TAY)) qa-labels))
(setq qa-once (r104-snapshot)) (bht:api-label-rotate "UCS")
(r104-check "repeat-is-idempotent" (equal qa-once (r104-snapshot) 1e-9))
(bht:lbl-sync-scope 'ALL)
(r104-check "sync-keeps-position-and-angle" (equal qa-once (r104-snapshot) 1e-9))
(bht:api-rtk-scale "1" "0.75")
(r104-check "scale-keeps-angle" (r104-angle-p (/ pi 6.0)))
(setq qa-rotated (r104-snapshot))
(r104-check "bad-mode-rejected" (= (car (bht:api-label-rotate "BAD")) "LOI"))
(r104-check "bad-mode-no-change" (equal qa-rotated (r104-snapshot)))
(setq qa-writer (eval 'bht:lbl-rotate-write))
(defun bht:lbl-rotate-write (plans)
 (entmod (caddr (car plans))) (/ 1 0))
(setq qa-rollback-result (bht:lbl-rotate 1.2))
(set 'bht:lbl-rotate-write qa-writer)
(r104-check "partial-write-failure-rolls-back-all" (and (= (car qa-rollback-result) 'LOI) (equal qa-rotated (r104-snapshot))))
(setq qa-test-box (entmakex '((0 . "TEXT") (10 30.0 20.0 0.0) (40 . 1.0) (1 . "BOX") (50 . 1.5707963267948966))))
(setq qa-tb (textbox (entget qa-test-box)))
(r104-check "90-degree-box-swaps-width-and-height" (equal (bht:text-box qa-test-box)
 (list (- 30.0 (cadadr qa-tb)) (+ 20.0 (caar qa-tb)) (- 30.0 (cadar qa-tb)) (+ 20.0 (caadr qa-tb))) 1e-8))
;; Undo is exercised at the top-level command prompt by run_rtk104.ps1.
;; A loaded Lisp file itself is a command group; undo inside it is not a user action.
(setq qa-ten (car (vl-remove-if-not '(lambda (e) (= (cadr (bht:xget e "BHT_NHAN")) "TEN")) qa-labels)))
(setq qa-anchor (cdr (assoc 10 (entget qa-ten))))
(bht:lbl-rotate pi)
(r104-check "cluster-anchored-to-survey-point"
 (equal (cdr (assoc 10 (entget qa-ten)))
  (bht:label-local (bht:pv (bht:pt-find (car (bht:xget qa-ten "BHT_NHAN")) (bht:pt-all)) 'xyz)
   (cdr (assoc 'off (bht:lbl-settings))) (cdr (assoc 'off (bht:lbl-settings))) pi) 1e-9))
(r104-check "reverse-direction-kept" (r104-angle-p pi))
(bht:layer "QA_LOCK" 7)
(entmod (bht:dxf-put (entget qa-ten) 8 "QA_LOCK"))
(command "_.-LAYER" "_Lock" "QA_LOCK" "")
(setq qa-locked-group (car (bht:xget qa-ten "BHT_NHAN")))
(setq qa-lock-before (mapcar '(lambda (e) (entget e '("*")))
 (vl-remove-if-not '(lambda (e) (= (car (bht:xget e "BHT_NHAN")) qa-locked-group)) qa-labels)))
(bht:lbl-rotate 0.0)
(r104-check "locked-cluster-entirely-kept" (equal qa-lock-before
 (mapcar '(lambda (e) (entget e '("*"))) (vl-remove-if-not '(lambda (e) (= (car (bht:xget e "BHT_NHAN")) qa-locked-group)) qa-labels))))
(command "_.-LAYER" "_Unlock" "QA_LOCK" "")
(entmod (bht:dxf-put (entget qa-ten) 8 "BHT_RTK_TEN"))
(bht:lbl-reset (list "QA-A" "QA-B"))
(r104-check "explicit-auto-reset-horizontal" (r104-angle-p 0.0))
(setq qa-before-pick (r104-snapshot))
(princ "\nRTK104-READY-FOR-PICK")
(princ)
