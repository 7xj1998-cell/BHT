;;; BHT 1.1.5 - phien D: tich hop thu vien bien bao TDTSolution 9.1 ban thuong.
(load "C:/Users/Le Bao/BHT_TEST_V044/t_common.lsp")
(vl-load-com)
(tbegin "D")
(setq e (tload))
(tchk "D00" "nạp BHT-5.0" (and (null e) (= *bht-version* "1.1.5")) e)
(setq nc (t-netload "BHT.Core.dll") nb (t-netload "BHT.Bridge.dll"))
(tchk "D01" "NETLOAD Core + Bridge 5.0" (and (null nc) (null nb)) (list nc nb))
(setq st (vl-catch-all-apply 'BHTTDT91STATUS nil))
(tchk "D02" "phát hiện TDTSolution 9.1 bản thường và danh mục 412 mã"
      (and (listp st) (= (car st) "OK") (= (atoi (nth 3 st)) 412)
           (wcmatch (strcase (nth 2 st)) "*TDT SOLUTION 2022")) st)
(setq r (vl-catch-all-apply 'BHTTDTBLOCK (list "W.225")))
(tchk "D03" "nạp W.225 từ DWG nguồn TDT" (and (listp r) (= (car r) "OK") (tblsearch "BLOCK" (cadr r))) r)
(setq ins (if (and (listp r) (= (car r) "OK")) (bht:insert (cadr r) '(0.0 0.0 0.0) "0" 1.0) nil))
(tlog (strcat "   INSERT=" (vl-princ-to-string ins) " ENT=" (vl-princ-to-string (if ins (entget ins) nil))))
(setq bd (if (and (listp r) (= (car r) "OK")) (tblobjname "BLOCK" (cadr r)) nil)
      cur (if bd (entnext bd) nil) face nil post nil foot nil)
(while (and cur (/= (cdr (assoc 0 (entget cur))) "ENDBLK"))
  (setq dd (entget cur))
  (cond ((= (cdr (assoc 0 dd)) "INSERT") (setq face dd))
        ((= (cdr (assoc 0 dd)) "LINE") (setq post dd))
        ((= (cdr (assoc 0 dd)) "CIRCLE") (setq foot dd)))
  (setq cur (entnext cur)))
(tchk "D04" "wrapper dùng đúng scale mặt TDT 0.2 và cột cao 0.6 unit"
      (and ins face post foot (equal (cdr (assoc 41 face)) 0.2 1e-9)
           (equal (distance (cdr (assoc 10 post)) (cdr (assoc 11 post))) 0.6 1e-9))
      (list (if face (cdr (assoc 41 face))) (if post (distance (cdr (assoc 10 post)) (cdr (assoc 11 post))))))
(setq r2 (vl-catch-all-apply 'BHTTDTBLOCK (list "W.225")))
(tchk "D05" "nạp lại cùng mã không nhân đôi định nghĩa" (and (listp r2) (= (car r2) "OK") (= (cadr r2) (cadr r))) r2)
(setq pl (entmakex '((0 . "LWPOLYLINE") (100 . "AcDbEntity") (8 . "0") (100 . "AcDbPolyline") (90 . 2) (70 . 0) (10 0.0 0.0) (10 10.0 0.0))))
(setq rr (if pl (vl-catch-all-apply 'BHTTDT91ROUTE (list (cdr (assoc 5 (entget pl))) "")) nil))
(tchk "D06" "không nhận Polyline thường là tim TDT" (and (listp rr) (= (car rr) "LOI")) rr)
(if ins (entdel ins))
(if pl (entdel pl))
(tend "D")
(princ)
