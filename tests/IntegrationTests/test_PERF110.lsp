(setq qa110-scan-fn bht:tagged-pairs qa110-scans 0 qa110-fails 0)
(defun bht:tagged-pairs (kind app n) (setq qa110-scans (1+ qa110-scans)) (qa110-scan-fn kind app n))
(setq qa110-source (list (bht:pt-all) (bht:rec-all "ROUTE") (bht:rec-all "SEG")))
(foreach qa110-task '("SYNC" "SCALE")
  (setq qa110-scans 0 qa110-start (getvar "MILLISECS"))
  (setq qa110-result (if (= qa110-task "SYNC") (bht:api-symbol-sync "") (bht:api-sign-display "3" "2" "PARALLEL")))
  (princ (strcat "\nQA110-PERF " qa110-task " MS=" (itoa (- (getvar "MILLISECS") qa110-start)) " SCANS=" (itoa qa110-scans)))
  (princ (strcat "\n" (if (= (car qa110-result) "OK") "PASS " "FAIL ") "QA110 " qa110-task)))
(princ (if (equal qa110-source (list (bht:pt-all) (bht:rec-all "ROUTE") (bht:rec-all "SEG"))) "\nPASS QA110 perf-source-unchanged" "\nFAIL QA110 perf-source-unchanged"))
(setq bht:tagged-pairs qa110-scan-fn)
(princ "\nQA110-DONE") (princ)
