(setq s119-n 0 s119-fail 0)
(defun s119-check (name ok) (setq s119-n (1+ s119-n)) (if (not ok) (setq s119-fail (1+ s119-fail))) (princ (strcat "\n" (if ok "PASS SEG119 " "FAIL SEG119 ") name)))
(defun s119-point (id x y / e) (setq e (entmakex (list '(0 . "POINT") (cons 10 (list x y 0.0))))) (bht:pt-write-xdata e id "QA" "1" "1" y x 0.0 "BIEN_BAO" "QA" "" ""))
(defun s119-route (id y loai / e) (setq e (entmakex (list '(0 . "LWPOLYLINE") '(100 . "AcDbEntity") '(100 . "AcDbPolyline") '(90 . 2) '(70 . 0) (cons 10 (list 0.0 y)) (cons 10 (list 1000.0 y)))))
  (bht:route-create id e loai 30.0 0.0 nil "SEG119") (bht:route-add-mark id 0.0 40000.0 40000.0 "QA" "") (bht:route-add-mark id 1000.0 41000.0 41000.0 "QA" ""))
(defun s119-seg (id route a b side) (bht:rec-write "SEG" id (list (cons "segment_id" id) '("package_id" . "GOI_01") (cons "route_id" route) (cons "km_start_m" a) (cons "km_end_m" b) (cons "side" side))))
(defun s119-sign (id x y) (s119-point (strcat id "-P") x y) (bht:obj-create id '(("nhom" . "BIEN_BAO") ("ma_hieu" . "W.207a")) (list (strcat id "-P")) T))
(defun s119-rec (id key) (bht:get (bht:obj-read id) key))
(s119-route "ROAD" 0.0 "TIM_DUONG") (s119-route "DITCH" 20.0 "TIM_RANH")
(s119-seg "ROAD-A" "ROAD" "40000" "40500" "HAI_BEN") (s119-seg "ROAD-B" "ROAD" "40500" "41000" "HAI_BEN")
(s119-seg "DITCH-A" "DITCH" "40000" "41000" "HAI_BEN")
(s119-sign "ROAD-SIGN" 250.0 2.0) (s119-sign "DITCH-SIGN" 300.0 19.0) (s119-sign "TIE" 200.0 10.0) (s119-sign "BOUNDARY" 500.0 -2.0)
(bht:meta-set "station_method" "ROUTE") (bht:meta-set "station_active_route" "ROAD")
(bht:station-objects) (setq s119-result (bht:assign-segments))
(s119-check "parallel-lines-use-own-segment-route" (and (= "ROAD-A" (s119-rec "ROAD-SIGN" "doan")) (= "DITCH-A" (s119-rec "DITCH-SIGN" "doan")) (= "DITCH" (s119-rec "DITCH-SIGN" "route_id"))))
(s119-check "station-from-bound-route" (= "40300.000" (s119-rec "DITCH-SIGN" "ly_trinh_m")))
(s119-check "near-equal-offsets-require-choice" (= "NHIEU_DOAN" (s119-rec "TIE" "gan_doan_pp")))
(s119-check "shared-station-boundary-requires-choice" (and (= "NHIEU_DOAN" (s119-rec "BOUNDARY" "gan_doan_pp")) (= "ROAD-A;ROAD-B" (s119-rec "BOUNDARY" "doan_ung_vien"))))
(s119-check "assignment-does-not-switch-active-route" (= "ROAD" (bht:meta "station_active_route" "")))
(bht:station-one "DITCH-SIGN")
(s119-check "single-object-respects-bound-ditch" (= "DITCH" (s119-rec "DITCH-SIGN" "route_id")))
(bht:station-objects)
(s119-check "bulk-station-respects-bound-ditch" (= "DITCH" (s119-rec "DITCH-SIGN" "route_id")))
(bht:route-recalculate "ROAD")
(s119-check "global-road-recalc-preserves-other-bound-route" (and (= "DITCH-A" (s119-rec "DITCH-SIGN" "doan")) (= "DITCH" (s119-rec "DITCH-SIGN" "route_id"))))
(bht:assign-manual "TIE" "DITCH-A") (bht:assign-segments)
(s119-check "manual-choice-keeps-own-route" (and (= "THU_CONG" (s119-rec "TIE" "gan_doan_pp")) (= "DITCH" (s119-rec "TIE" "route_id"))))
(bht:meta-set "station_method" "FIELD_MARKERS") (bht:station-one "DITCH-SIGN")
(s119-check "bound-route-overrides-field-mode-for-single-object" (= "DITCH" (s119-rec "DITCH-SIGN" "route_id")))
(bht:station-objects)
(s119-check "bound-route-preserves-assignment-in-bulk-field-mode" (and (= "DITCH" (s119-rec "DITCH-SIGN" "route_id")) (= "DITCH-A" (s119-rec "DITCH-SIGN" "doan"))))
(s119-seg "SIDE-ONLY" "DITCH" "40000" "41000" "PHAI")
(s119-check "segment-road-side-is-not-ditch-side" (not (vl-some '(lambda (o) (= (car o) "SIDE-ONLY")) (bht:seg-options (bht:set (bht:obj-read "DITCH-SIGN") "phia_duong" "TRAI") '(300.0 19.0 0.0) (bht:seg-all) (bht:pt-all)))))
(bht:rec-delete "SEG" "SIDE-ONLY")
(bht:meta-set "station_method" "ROUTE")
(bht:route-edit "DITCH" "DITCH-NEW" "TIM_RANH" 30.0 0.0)
(s119-check "rename-updates-segment-reference" (= "DITCH-NEW" (bht:get (bht:rec-read "SEG" "DITCH-A") "route_id")))
(bht:station-one "DITCH-SIGN")
(s119-check "renamed-route-recalculates" (= "DITCH-NEW" (s119-rec "DITCH-SIGN" "route_id")))
(setq s119-before (bht:rec-all "OBJ") s119-write bht:obj-write s119-count 0)
(defun bht:obj-write (id rec) (setq s119-count (1+ s119-count)) (if (= s119-count 2) nil (s119-write id rec)))
(setq s119-error (vl-catch-all-apply 'bht:assign-segments nil)) (setq bht:obj-write s119-write) (princ (strcat "\nFAULT119=" (if (vl-catch-all-error-p s119-error) (vl-catch-all-error-message s119-error) (vl-princ-to-string s119-error))))
(s119-check "failed-assignment-rolls-back-all-records" (and (not (vl-catch-all-error-p s119-error)) (eq (car s119-error) 'LOI) (equal s119-before (bht:rec-all "OBJ"))))
(setq s119-route-record (bht:route-read "DITCH-NEW")) (bht:route-delete "DITCH-NEW")
(setq s119-before (bht:rec-all "OBJ") s119-error (bht:assign-segments))
(s119-check "missing-route-aborts-without-fallback-or-partial-assignment" (and (not (vl-catch-all-error-p s119-error)) (eq (car s119-error) 'LOI) (equal s119-before (bht:rec-all "OBJ")) (= "DITCH-NEW" (bht:get (bht:rec-read "SEG" "DITCH-A") "route_id"))))
(bht:route-write "DITCH-NEW" s119-route-record) (bht:assign-segments)
(bht:route-write "DITCH-NEW" (bht:set-all (bht:set s119-route-record "station_source" "TDT_STAKES") "moc" nil))
(setq s119-before (bht:rec-all "OBJ") s119-error (bht:assign-segments))
(s119-check "missing-controls-block-without-partial-write" (and (eq (car s119-error) 'LOI) (equal s119-before (bht:rec-all "OBJ"))))
(bht:route-write "DITCH-NEW" s119-route-record)
(s119-sign "NUMBERED" 400.0 20.0)
(bht:obj-write "NUMBERED" (bht:set (bht:set (bht:set (bht:obj-read "NUMBERED") "nhom" "COC_TIEU") "marker_km" "40") "marker_h" "4"))
(bht:station-objects) (bht:assign-segments)
(s119-check "observed-marker-km-preserved-and-assigned" (and (= "40400.000" (s119-rec "NUMBERED" "ly_trinh_m")) (= "DITCH-A" (s119-rec "NUMBERED" "doan")) (= "DITCH-NEW" (s119-rec "NUMBERED" "route_id"))))
(princ (strcat "\nSEG119-CHECKS=" (itoa s119-n) " FAIL=" (itoa s119-fail))) (princ)
