;;; BHTSEG/1: native portable segment tables, XLSX import handled by .NET.
(defun bht:seg-load (path replace / result)
  (if (not (bht:bridge-load 'BHTSEGLOAD)) (progn (bht:err "Cần BHT.Bridge.dll cùng phiên bản để đọc bảng đoạn.") nil)
    (progn
      (setq result (BHTSEGLOAD path (if replace 1 0)))
      (if (= (substr result 1 3) "OK|") (atoi (substr result 4)) (progn (bht:err result) nil)))))

(defun bht:seg-all ()
  (vl-sort (bht:rec-all "SEG") '(lambda (a b / x y)
    (setq x (bht:num (bht:get (cdr a) "km_start_m")) y (bht:num (bht:get (cdr b) "km_start_m")))
    (if (equal x y 1e-9) (< (car a) (car b)) (< x y)))))

;; A missing referenced route remains explicit; never fall back to the global route.
(defun bht:seg-route (rec / seg)
  (setq seg (bht:rec-read "SEG" (bht:get rec "doan")))
  (if seg (bht:get seg "route_id") ""))
(defun bht:station-for-object (rec pos index / id route)
  (setq id (bht:seg-route rec))
  (cond ((= id "") (bht:station-object rec index pos))
    ((setq route (bht:route-read id)) (bht:station-object-route route rec index pos))
    (T (list '(status . "CHUA_CO_TUYEN") (cons 'route id) (cons 'note (strcat "Tim của đoạn đã mất: " id))))))
(defun bht:seg-side (rec result bound)
  (cond ((member (bht:get rec "phia_duong") '("TRAI" "PHAI")) (bht:get rec "phia_duong"))
    ((and (= (cdr (assoc 'loai result)) "TIM_DUONG") (member (cdr (assoc 'side result)) '("TRAI" "PHAI"))) (cdr (assoc 'side result)))
    (T nil)))
(defun bht:seg-in-range (station side seg / a b ss)
  (setq a (bht:num (bht:get seg "km_start_m")) b (bht:num (bht:get seg "km_end_m")) ss (bht:get seg "side"))
  (and station a b (>= station (- a 1e-6)) (<= station (+ b 1e-6)) (or (null side) (= ss "HAI_BEN") (= ss side))))
(defun bht:seg-candidates (station side segs / out seg)
  (foreach seg segs (if (bht:seg-in-range station side (cdr seg)) (setq out (cons (car seg) out)))) (acad_strlsort out))

(defun bht:seg-station-record (rec result / st key observed)
  (setq st (cdr (assoc 'status result)) observed (bht:obj-marker-metres rec))
  (foreach key '("field_chain_id" "field_pair_a" "field_pair_b" "field_last_error") (setq rec (bht:set rec key "")))
  (setq rec (bht:set rec "station_source" "ROUTE") rec (bht:set rec "route_id" (bht:str (cdr (assoc 'route result))))
        rec (bht:set rec "trang_thai_km" st) rec (bht:set rec "station_status" (bht:station-status-v5 st))
        rec (bht:set rec "ly_trinh_m" (if (bht:station-determined st) (bht:fnum (cdr (assoc 'station result)) 3) ""))
        rec (bht:set rec "ly_trinh_km" (if (bht:station-determined st) (bht:fmt-km (cdr (assoc 'station result))) ""))
        rec (bht:set rec "offset_m" (if (cdr (assoc 'offset result)) (bht:fnum (cdr (assoc 'offset result)) 3) ""))
        rec (bht:set rec "phia_tuyen" (bht:str (cdr (assoc 'side result)))) rec (bht:set rec "loai_tuyen" (bht:str (cdr (assoc 'loai result))))
        rec (bht:set rec "station_route_revision" (if (cdr (assoc 'revision result)) (itoa (cdr (assoc 'revision result))) ""))
        rec (bht:set rec "nguon_km" (bht:str (cdr (assoc 'note result)))))
  (setq rec (bht:station-point-record rec result))
  (if observed
    (setq rec (bht:set rec "ly_trinh_m" (bht:fnum observed 3)) rec (bht:set rec "ly_trinh_km" (bht:fmt-km observed))
          rec (bht:set rec "station_source" "NUMBERED_MARKER") rec (bht:set rec "nguon_km" "Số Km/H đã nhập")
          rec (bht:set rec "trang_thai_km" "NHAP_TAY") rec (bht:set rec "station_status" "MANUAL") rec (bht:set rec "station_route_revision" ""))) rec)

;; Calculate independently on every bound route. Nearest eligible route wins;
;; equal offsets (1 cm) and overlapping intervals on the same route stay ambiguous.
(defun bht:seg-options (rec pos segs index / options id result route cached station side offset observed seg)
  (setq observed (bht:obj-marker-metres rec))
  (foreach seg segs
    (setq id (bht:get (cdr seg) "route_id"))
    (if (= id "")
      (setq result (list (cons 'status (bht:get rec "trang_thai_km")) (cons 'station (bht:num (bht:get rec "ly_trinh_m")))
        (cons 'side (bht:get rec "phia_tuyen")) (cons 'loai (bht:get rec "loai_tuyen"))) offset nil)
      (progn
        (if (not (assoc id cached)) (setq cached (cons (cons id (if pos (bht:station-object-route (bht:route-read id) rec index pos) '((status . "KHONG_CO_VI_TRI")))) cached)))
        (setq result (cdr (assoc id cached)) offset (cdr (assoc 'offset result)))))
    (setq station (if observed observed (cdr (assoc 'station result))) side (bht:seg-side rec result (/= id "")))
    (if (and (or (bht:station-determined (cdr (assoc 'status result))) (and (= id "") (= (cdr (assoc 'status result)) "NHAP_TAY"))) (bht:seg-in-range station side (cdr seg)))
      (setq options (cons (list (car seg) result offset) options))))
  options)
(defun bht:seg-nearest (options / distances nearest)
  (setq distances (vl-remove nil (mapcar 'caddr options)))
  (if distances
    (progn (setq nearest (apply 'min distances))
      (vl-remove-if '(lambda (o) (and (numberp (caddr o)) (> (caddr o) (+ nearest 0.01)))) options))
    options))
(defun bht:seg-clear (rec pp candidates)
  (bht:set (bht:set (bht:set (bht:set rec "doan" "") "goi" "") "gan_doan_pp" pp) "doan_ung_vien" candidates))

(defun bht:seg-outside-status (rec / station route)
  (setq station (bht:num (bht:get rec "ly_trinh_m")) route (bht:get rec "route_id"))
  (if (vl-some '(lambda (p) (and (member (bht:get (cdr p) "route_id") (list "" route)) (bht:seg-in-range station nil (cdr p)))) (bht:seg-all))
    "KHAC_PHIA_DUONG" "NGOAI_PHAM_VI"))

;; Refresh membership from the just-calculated station without switching its route.
(defun bht:seg-refresh-record (rec / segs candidates seg result station side id)
  (setq segs (bht:seg-all))
  (if (and segs (not (and (= (bht:get rec "gan_doan_pp") "THU_CONG") (bht:rec-read "SEG" (bht:get rec "doan")))))
    (progn
      (setq result (list (cons 'loai (bht:get rec "loai_tuyen")) (cons 'side (bht:get rec "phia_tuyen")))
            station (bht:num (bht:get rec "ly_trinh_m")) side (bht:seg-side rec result nil))
      (if (or (bht:station-determined (bht:get rec "trang_thai_km")) (= (bht:get rec "trang_thai_km") "NHAP_TAY"))
        (foreach seg segs
          (setq id (bht:get (cdr seg) "route_id"))
          (if (and (or (= id "") (= id (bht:get rec "route_id"))) (bht:seg-in-range station side (cdr seg)))
            (setq candidates (cons (car seg) candidates)))))
      (cond ((= (length candidates) 1)
              (setq id (car candidates) seg (bht:rec-read "SEG" id)
                    rec (bht:set (bht:set (bht:set (bht:set rec "doan" id) "goi" (bht:get seg "package_id")) "doan_ung_vien" id)
                      "gan_doan_pp" (if (= (bht:get rec "trang_thai_km") "NOI_SUY") "TU_DONG" "TU_DONG_CAN_XAC_NHAN"))))
            (candidates (setq rec (bht:seg-clear rec "NHIEU_DOAN" (bht:join (acad_strlsort candidates) ";"))))
            (T (setq rec (bht:seg-clear rec (if station (bht:seg-outside-status rec) "CHUA_XAC_DINH_KM") "")))))) rec)

(defun bht:assign-segments-write (/ segs index rec pos options chosen result st auto amb out und manual seg id route failed controls s oid routes key option *bht-control-cache*)
  (setq segs (bht:seg-all) index (bht:pt-all) auto 0 amb 0 out 0 und 0 manual 0)
  (setq *bht-control-cache* (mapcar '(lambda (p) (cons (car p) (bht:route-object-controls (cdr p)))) (bht:rec-all "ROUTE")))
  ;; Validate all explicit links before writing any object.
  (foreach s segs
    (setq id (bht:get (cdr s) "route_id"))
    (if (/= id "")
      (progn
        (setq route (bht:route-read id) controls (cdr (assoc id *bht-control-cache*)))
        (cond ((null route) (setq failed (strcat "Đoạn " (car s) " thiếu tim " id ". Chọn lại tim trong bảng đoạn.")))
          ((null (bht:route-ent route)) (setq failed (strcat "Tim " id " đã mất hình học. Chọn lại tim trước khi phân đoạn.")))
          ((or (cadr controls) (< (length (car controls)) 2)) (setq failed (strcat "Tim " id " cần ít nhất hai mốc lý trình hợp lệ; kiểm tra mốc trước khi phân đoạn.")))))))
  (foreach oid (if failed nil (bht:progress-open-ids))
    (setq rec (bht:obj-read oid) pos (bht:obj-position rec index))
    (if (and (= (bht:get rec "gan_doan_pp") "THU_CONG") (bht:rec-read "SEG" (bht:get rec "doan")))
      (progn
        (if (/= (bht:seg-route rec) "")
          (setq rec (bht:seg-station-record rec (if pos (bht:station-for-object rec pos index) '((status . "KHONG_CO_VI_TRI"))))))
        (setq manual (1+ manual)))
      (progn
        (setq options (bht:seg-nearest (bht:seg-options rec pos segs index)))
        (cond
          ((= (length options) 1)
            (setq chosen (car options) seg (bht:rec-read "SEG" (car chosen)) result (cadr chosen) st (cdr (assoc 'status result)))
            (if (/= (bht:get seg "route_id") "") (setq rec (bht:seg-station-record rec result)))
            (setq rec (bht:set rec "doan" (car chosen)) rec (bht:set rec "goi" (bht:get seg "package_id"))
                  rec (bht:set rec "doan_ung_vien" (car chosen)) rec (bht:set rec "gan_doan_pp" (if (= st "NOI_SUY") "TU_DONG" "TU_DONG_CAN_XAC_NHAN")) auto (1+ auto)))
          (options
            (setq routes nil)
            (foreach option options
              (setq id (bht:get (bht:rec-read "SEG" (car option)) "route_id"))
              (if (not (member id routes)) (setq routes (cons id routes))))
            (if (and (> (length routes) 1) (not (bht:obj-marker-metres rec)))
              (progn
                (foreach key '("route_id" "ly_trinh_m" "ly_trinh_km" "offset_m" "station_route_revision" "phia_tuyen" "loai_tuyen") (setq rec (bht:set rec key "")))
                (setq rec (bht:station-point-record rec nil))
                (setq rec (bht:set (bht:set (bht:set rec "trang_thai_km" "NHIEU_TIM") "station_status" "AMBIGUOUS_ROUTE") "nguon_km" "Nhiều đoạn dùng tim khác nhau phù hợp; cần chọn đoạn."))))
            (setq rec (bht:seg-clear rec "NHIEU_DOAN" (bht:join (acad_strlsort (mapcar 'car options)) ";")) amb (1+ amb)))
          ((not (bht:station-determined (bht:get rec "trang_thai_km"))) (setq rec (bht:seg-clear rec "CHUA_XAC_DINH_KM" "") und (1+ und)))
          (T (setq rec (bht:seg-clear rec (bht:seg-outside-status rec) "") out (1+ out))))))
    (if (and (not failed) (not (bht:obj-write oid rec))) (setq failed (strcat "Không ghi được hồ sơ " oid))))
  (if failed (list 'LOI failed)
    (progn (bht:kh-station-label-refresh nil)
      (list (cons 'auto auto) (cons 'ambiguous amb) (cons 'outside out) (cons 'undetermined und) (cons 'manual manual)))))
(defun bht:assign-segments () (bht:kh-display-transaction 'bht:assign-segments-write nil))

(defun bht:assign-manual-write (oid segid / rec seg index pos result)
  (setq rec (bht:obj-read oid) seg (bht:rec-read "SEG" segid))
  (cond ((null rec) (list nil "Không có hồ sơ.")) ((null seg) (list nil "Không có đoạn; nạp bảng trước."))
    ((and (/= (bht:get seg "route_id") "") (not (bht:route-read (bht:get seg "route_id")))) (list nil "Tim của đoạn đã mất. Gán lại tim trước."))
    (T
      (setq rec (bht:set (bht:set (bht:set rec "doan" (strcase segid)) "goi" (bht:get seg "package_id")) "gan_doan_pp" "THU_CONG"))
      (if (/= (bht:get seg "route_id") "")
        (progn (setq index (bht:pt-all) pos (bht:obj-position rec index)
          result (if pos (bht:station-for-object rec pos index) '((status . "KHONG_CO_VI_TRI"))))
          (setq rec (bht:seg-station-record rec result))))
      (if (not (bht:obj-write oid rec)) (list 'LOI "Không ghi được hồ sơ.")
        (progn (bht:kh-station-label-refresh (list oid)) (list T segid))))))
(defun bht:assign-manual (oid segid / result)
  (setq result (bht:kh-display-transaction 'bht:assign-manual-write (list oid segid)))
  (if (eq (car result) 'LOI) (list nil (cadr result)) result))

;; Context excludes drawing handles so it survives export/import. No object is
;; recalculated while checking an existing confirmation.
(defun bht:progress-context (seg route / keys)
  (setq keys '("loai" "start_dist" "direction" "chieu" "max_offset" "ngoai_suy_m" "route_revision" "station_control_mode"))
  (vl-prin1-to-string (list (mapcar '(lambda (k) (cons k (bht:get route k))) keys)
    (mapcar '(lambda (m) (list (car m) (cadr m) (caddr m))) (car (bht:route-controls route)))
    (mapcar '(lambda (k) (cons k (bht:get seg k))) '("km_start_m" "km_end_m" "side")))))
(defun bht:progress-route-state (route / rec key)
  (foreach key '("loai" "start_dist" "direction" "chieu" "max_offset" "ngoai_suy_m" "route_revision" "station_control_mode" "station_source")
    (setq rec (append rec (list (cons key (bht:get route key))))))
  (bht:join (mapcar 'cdr (bht:rec-encode (bht:set-all rec "moc" (bht:get-all route "moc")))) (chr 10)))
(defun bht:progress-point-snapshot (rec index / out pid matches xyz)
  (foreach pid (bht:get-all rec "pt")
    (setq matches (vl-remove-if-not '(lambda (p) (= (car p) (strcase pid))) index))
    (if (/= (length matches) 1) (vl-exit-with-error (strcat "Điểm thiếu hoặc trùng mã: " pid)))
    (setq xyz (bht:pv (cdar matches) 'xyz))
    (setq out (append out (list (bht:join (cons pid (mapcar '(lambda (n) (bht:fnum n 8)) xyz)) "|")))))
  (if (null out) (vl-exit-with-error "Hồ sơ chưa có điểm khảo sát.")) out)
(defun bht:progress-check-locked (segid routeid / seg route index context pair rec saved actual error-result)
  (setq seg (bht:rec-read "SEG" segid) route (bht:route-read routeid) index (bht:pt-all)
        context (bht:progress-context seg route))
  (foreach pair (bht:rec-all "OBJ")
    (setq rec (cdr pair))
    (if (and (= (bht:get rec "doan") segid) (bht:progress-locked rec))
      (progn
        (setq saved (bht:get rec "progress_context")
              actual (vl-catch-all-apply 'bht:progress-point-snapshot (list rec index)))
        (if (or (/= (bht:get seg "route_id") routeid) (/= (bht:get rec "route_id") routeid)
                (/= (bht:get rec "goi") (bht:get seg "package_id"))
                (and (/= (bht:get rec "station_route_revision") "")
                     (/= (bht:get rec "station_route_revision") (itoa (bht:route-revision route))))
                (= (bht:get rec "progress_route_signature") "")
                (not (equal (cdr (bht:split (bht:get rec "progress_route_signature") "|"))
                            (cdr (bht:split (bht:get route "geometry_signature") "|"))))
                (vl-catch-all-error-p actual) (not (equal actual (bht:get-all rec "progress_point")))
                (and (/= saved "") (/= saved context))
                (and (/= (bht:get rec "progress_route_state") "") (/= (bht:get rec "progress_route_state") (bht:progress-route-state route)))
                ;; Legacy auto controls have no verifiable frozen context.
                (and (= saved "") (or (= (bht:get rec "station_route_revision") "")
                  (not (equal (car (bht:route-controls route)) (vl-sort (bht:route-marks route) '(lambda (a b) (< (car a) (car b)))))))))
          (setq error-result (list 'LOI (strcat "Hồ sơ đã xác nhận " (car pair) ": tim, mốc, điểm hoặc phân đoạn đã đổi/chưa đủ bằng chứng. Đối chiếu trước khi bổ sung; kết quả cũ được giữ nguyên.")))))))
  error-result)

;; A rolling pass only changes eligible, unfinished objects of the chosen segment.
(defun bht:progress-plan (segid routeid / seg route valid index rows updates rec oid pos result st station side reason eligible old manual pair *bht-control-cache*)
  (setq seg (bht:rec-read "SEG" segid) route (bht:route-read routeid))
  (cond ((null seg) (list 'LOI "Chọn đoạn trong bảng đã nạp."))
    ((null route) (list 'LOI "Chọn tim của bản vẽ đoạn hiện tại."))
    ((eq (car (setq valid (bht:route-recalculate-plan routeid))) 'LOI) valid)
    ((setq valid (bht:progress-check-locked segid routeid)) valid)
    (T
      (setq index (bht:pt-all) *bht-control-cache* (list (cons routeid (bht:route-controls route))))
      (foreach pair (bht:rec-all "OBJ")
        (setq oid (car pair) rec (cdr pair) old (bht:get rec "doan") eligible nil
              manual (and (= old segid) (= (bht:get rec "gan_doan_pp") "THU_CONG"))
              result nil reason nil station nil)
        (cond ((bht:progress-locked rec) (setq reason "Giữ kết quả đã xác nhận"))
          ((and (/= old "") (/= old segid)) (setq reason (strcat "Giữ hồ sơ thuộc " old)))
          (T
            (setq pos (bht:obj-position rec index)
                  result (if pos (bht:station-object-route route rec index pos) '((status . "KHONG_CO_VI_TRI")))
                  st (cdr (assoc 'status result)) station (if (bht:obj-marker-metres rec) (bht:obj-marker-metres rec) (cdr (assoc 'station result)))
                  side (bht:seg-side rec result T))
            (cond ((not (bht:station-determined st)) (setq reason (strcat "Chưa tính được: " st)))
              ((not (bht:seg-in-range station nil seg)) (setq reason "Ngoài khoảng lý trình; gán tay không bỏ qua kiểm tra phạm vi"))
              ((and (null side) (/= (bht:get seg "side") "HAI_BEN")) (setq reason "Chưa rõ phía đường; kiểm tra thuộc tính phía đường"))
              ((not (bht:seg-in-range station side seg)) (setq reason "Khác phía đường"))
              (T (setq eligible T reason (if manual "Tính theo đoạn đã gán tay" "Tính bổ sung vào đoạn"))))))
        (if eligible
          (progn
            (setq rec (bht:seg-station-record rec result)
                  rec (bht:set (bht:set (bht:set rec "doan" segid) "goi" (bht:get seg "package_id")) "doan_ung_vien" segid)
                  rec (bht:set rec "gan_doan_pp" (if manual "THU_CONG" "TU_DONG"))
                  rec (bht:set (bht:set rec "progress_state" "TINH_XONG") "progress_locked" "0"))
            (setq updates (cons (cons oid rec) updates))))
        (setq rows (cons (bht:join (list oid (bht:get rec "ma_hieu") (if station (bht:fmt-km station) (bht:get rec "ly_trinh_km")) old reason) (chr 9)) rows)))
      (list segid routeid (reverse updates) (reverse rows)
        (list (bht:rec-all "OBJ") seg route (bht:pt-all) (bht:progress-context seg route))))))

(defun bht:progress-write (plan / pair seg fresh)
  (setq fresh (bht:progress-plan (car plan) (cadr plan)))
  (if (or (eq (car fresh) 'LOI) (not (equal plan fresh)))
    (vl-exit-with-error "Dữ liệu đã đổi sau xem trước. Lập lại phương án trước khi áp dụng."))
  (setq seg (bht:rec-read "SEG" (car plan)))
  (if (/= (bht:get seg "route_id") (cadr plan))
    (if (not (bht:rec-write "SEG" (car plan) (bht:set (bht:set seg "route_id" (cadr plan)) "progress_state" "DANG_LAM"))) (vl-exit-with-error "Không lưu được tim của đoạn.")))
  (foreach pair (nth 2 plan) (if (not (bht:obj-write (car pair) (cdr pair))) (vl-exit-with-error "Không lưu được kết quả hồ sơ.")))
  (if (not (and (bht:meta-set "progress_active_segment" (car plan))
               (bht:meta-set "station_active_route" (cadr plan)) (bht:meta-set "station_method" "ROUTE")))
    (vl-exit-with-error "Không lưu được trạng thái xử lý đoạn."))
  (bht:kh-station-label-refresh (mapcar 'car (nth 2 plan)))
  (list T (strcat "Đã tính " (itoa (length (nth 2 plan))) " hồ sơ của " (car plan) ". Kết quả đoạn khác giữ nguyên.")))
(defun bht:progress-apply (plan / before result)
  (cond ((eq (car plan) 'LOI) plan)
    ((null (nth 2 plan)) (list 'NO_CHANGE "Không có hồ sơ chưa khóa đủ điều kiện. Không thay đổi dữ liệu."))
    (T (setq before (bht:rec-read "SEG" (car plan)) result (bht:kh-display-transaction 'bht:progress-write (list plan)))
       (if (and (eq (car result) 'LOI) (not (equal before (bht:rec-read "SEG" (car plan))))) (bht:rec-write "SEG" (car plan) before)) result)))

(defun bht:progress-finish (segid / seg route plan assigned updates bad pair next fields index pid point record pending)
  (setq seg (bht:rec-read "SEG" segid) route (bht:get seg "route_id")
        assigned (vl-remove-if-not '(lambda (p) (= (bht:get (cdr p) "doan") segid)) (bht:rec-all "OBJ")))
  (setq pending (vl-remove-if '(lambda (p) (bht:progress-locked (cdr p))) assigned))
  (cond ((null assigned) (list 'LOI "Đoạn chưa có hồ sơ để xác nhận."))
    ((null pending) (list 'NO_CHANGE "Tất cả hồ sơ đã khóa. Không tạo lần xác nhận mới."))
    ((eq (car (setq plan (bht:progress-plan segid route))) 'LOI) plan)
    (T
      (setq fields '("route_id" "ly_trinh_m" "ly_trinh_km" "offset_m" "phia_tuyen" "loai_tuyen" "station_route_revision" "station_point_id" "station_point_method" "station_point_e" "station_point_n" "station_projection_e" "station_projection_n" "trang_thai_km" "station_status" "station_source" "doan" "goi"))
      (foreach pair pending
        (setq next (cdr (assoc (car pair) (nth 2 plan))))
        (if (or (null next) (vl-some '(lambda (k) (/= (bht:get (cdr pair) k) (bht:get next k))) fields)) (setq bad (cons (car pair) bad))))
      (if bad (list 'LOI (strcat "Hồ sơ chưa tính hoặc đã đổi: " (bht:join bad ", ") ". Tính đoạn và kiểm tra trước khi xác nhận."))
        (progn
          (setq index (bht:pt-all))
          (foreach pair pending
            (setq record (bht:set-all (cdr pair) "progress_point" nil))
            (setq record (bht:set-all record "progress_point" (bht:progress-point-snapshot record index)))
            (setq record (bht:set record "progress_context" (bht:progress-context seg (bht:route-read route))))
            (setq record (bht:set record "progress_route_state" (bht:progress-route-state (bht:route-read route))))
            (setq record (bht:set record "progress_route_signature" (bht:get (bht:route-read route) "geometry_signature")))
            (if (not (bht:obj-write (car pair) (bht:set (bht:set (bht:set record "progress_locked" "1") "progress_state" "DA_DUYET") "progress_confirmed_at" (bht:now)))) (vl-exit-with-error "Không lưu được trạng thái xác nhận.")))
          (list T (strcat "Đã xác nhận bổ sung " (itoa (length pending)) " hồ sơ thuộc " segid ". Các hồ sơ đã khóa giữ nguyên.")))))))
;; Read-only validation/calculation for one correction. Never writes OBJ/RTK/ROUTE.
(defun bht:correction-evaluate (id encoded kind / old rec seg route ent controls index actual saved result side start dir)
  (setq old (bht:obj-read id) rec (read encoded) index (bht:pt-all))
  (if (not (bht:progress-locked old)) (vl-exit-with-error "Hồ sơ chưa được xác nhận."))
  (setq seg (bht:rec-read "SEG" (bht:get old "doan")) route (bht:route-read (bht:get old "route_id")))
  (if (or (null seg) (null route) (/= (bht:get seg "route_id") (bht:get old "route_id")) (/= (bht:get seg "package_id") (bht:get old "goi")))
    (vl-exit-with-error "Liên kết tim/đoạn/gói hiện hành không nhất quán."))
  (setq actual (bht:progress-point-snapshot old index) saved (bht:get old "progress_context"))
  (setq ent (bht:route-ent route) start (bht:num (bht:get route "start_dist")) dir (if (= (bht:int (bht:get route "direction")) -1) -1 1))
  (if (or (null ent) (/= (bht:get route "geometry_signature") (bht:route-geometry-signature ent (if start start 0.0) dir)))
    (vl-exit-with-error "Hình học tim của kết quả cũ đã đổi. Cần đối chiếu trước khi chuyển đoạn."))
  (if (or (not (equal actual (bht:get-all old "progress_point"))) (= (bht:get old "progress_route_signature") "")
          (not (equal (cdr (bht:split (bht:get old "progress_route_signature") "|")) (cdr (bht:split (bht:get route "geometry_signature") "|"))))
          (and (/= saved "") (/= saved (bht:progress-context seg route)))
          (and (/= (bht:get old "progress_route_state") "") (/= (bht:get old "progress_route_state") (bht:progress-route-state route)))
          (and (/= (bht:get old "station_route_revision") "") (/= (bht:get old "station_route_revision") (itoa (bht:route-revision route)))))
    (vl-exit-with-error "Điểm, tim hoặc mốc đã đổi so với lần xác nhận. Đối chiếu nguồn trước."))
  (if (and (= saved "") (or (= (bht:get old "station_route_revision") "")
      (not (equal (car (bht:route-controls route)) (vl-sort (bht:route-marks route) '(lambda (a b) (< (car a) (car b))))))))
    (vl-exit-with-error "Hồ sơ cũ thiếu bằng chứng mốc/tim; chưa thể hiệu chỉnh an toàn."))
  (if (and (/= kind "Attributes") (bht:obj-marker-metres old))
    (vl-exit-with-error "Cọc Km/H có thể là mốc cho hồ sơ khác; chưa hỗ trợ sửa điểm/lý trình tại đây."))
  (setq seg (bht:rec-read "SEG" (bht:get rec "doan")) route (if seg (bht:route-read (bht:get seg "route_id"))))
  (if (or (null seg) (null route)) (vl-exit-with-error "Chọn đoạn có tim hợp lệ."))
  (setq ent (bht:route-ent route) start (bht:num (bht:get route "start_dist")) dir (if (= (bht:int (bht:get route "direction")) -1) -1 1))
  (if (or (null ent) (not (car (bht:route-check-ent ent)))
      (/= (bht:get route "geometry_signature") (bht:route-geometry-signature ent (if start start 0.0) dir)))
    (vl-exit-with-error "Hình học tim đã đổi hoặc không hợp lệ."))
  (setq controls (bht:route-controls route))
  (if (or (cadr controls) (< (length (car controls)) 2) (not (bht:controls-valid-p (car controls))))
    (vl-exit-with-error "Mốc lý trình của tim chưa hợp lệ."))
  (if (or (not (member kind '("Attributes" "Retire"))) (/= (bht:get old "so_tru") (bht:get rec "so_tru")))
    (progn
      (setq actual (bht:progress-point-snapshot rec index)
            result (bht:station-object-route route rec index (bht:obj-position rec index)) side (bht:seg-side rec result T))
      (if (or (not (bht:station-determined (cdr (assoc 'status result))))
              (and (null side) (/= (bht:get seg "side") "HAI_BEN"))
              (not (bht:seg-in-range (cdr (assoc 'station result)) side seg)))
        (vl-exit-with-error "Điểm/lý trình/phía đường không thuộc đoạn chọn. Chọn đúng đoạn rồi xem trước lại."))
      (setq rec (bht:seg-station-record rec result)
            rec (bht:set (bht:set rec "goi" (bht:get seg "package_id")) "doan_ung_vien" (bht:get rec "doan"))
            rec (if (/= (bht:get old "doan") (bht:get rec "doan")) (bht:set rec "gan_doan_pp" "THU_CONG") rec)
            rec (bht:set-all rec "progress_point" actual)
            rec (bht:set rec "progress_context" (bht:progress-context seg route))
            rec (bht:set rec "progress_route_state" (bht:progress-route-state route))
            rec (bht:set rec "progress_route_signature" (bht:get route "geometry_signature")))))
  (mapcar 'cdr (bht:rec-encode rec)))

(defun bht:progress-reopen (segid / pair n)
  (if (vl-some '(lambda (p) (and (= (bht:get (cdr p) "doan") segid) (/= (bht:get (cdr p) "revision_id") ""))) (bht:rec-all "OBJ"))
    (vl-exit-with-error "Đoạn có lịch sử hiệu chỉnh. Dùng Hiệu chỉnh hồ sơ đã xác nhận cho từng đối tượng."))
  (setq n 0)
  (foreach pair (bht:rec-all "OBJ")
    (if (and (= (bht:get (cdr pair) "doan") segid) (bht:progress-locked (cdr pair)))
      (progn (bht:obj-write (car pair) (bht:set (bht:set (cdr pair) "progress_locked" "0") "progress_state" "MO_LAI")) (setq n (1+ n)))))
  (list T (strcat "Đã mở lại " (itoa n) " hồ sơ của " segid "; giữ kết quả để đối chiếu.")))

(defun bht:progress-preview-open (title plan / token)
  (setq *bht-preview-sequence* (1+ (if (numberp *bht-preview-sequence*) *bht-preview-sequence* 0))
        token (strcat (bht:now) "-" (itoa *bht-preview-sequence*))
        *bht-progress-pending* (list token plan))
  (BHTPROGRESSPREVIEW title (cons (strcat "@PLAN:" (if (nth 2 plan) token "")) (nth 3 plan))))

(defun bht:progress-preview-apply (token / plan result own)
  (if (or (= token "") (/= token (car *bht-progress-pending*)))
    (list 'LOI "Bảng xem trước đã hết hiệu lực. Mở lại Tính bổ sung trên đúng bản vẽ.")
    (progn
      (setq plan (cadr *bht-progress-pending*) own (= 0 (logand 8 (getvar "UNDOCTL"))))
      (if own (command-s "_.UNDO" "_Begin"))
      (setq result (vl-catch-all-apply 'bht:progress-apply (list plan)))
      (if own (command-s "_.UNDO" "_End"))
      (setq *bht-progress-pending* nil)
      (if (vl-catch-all-error-p result) (list 'LOI (vl-catch-all-error-message result)) result))))

(defun c:BHTXULYDOAN (/ *error* choice action seg route plan result own)
  (defun *error* (msg) (if own (command-s "_.UNDO" "_End")) (bht:on-error msg))
  (if (bht:palette-load)
    (progn
      (setq choice (BHTPROGRESSFORM) action (car choice) seg (cadr choice) route (caddr choice))
      (if (member action '("CALCULATE" "FINISH" "REOPEN"))
        (progn
          (setq plan (if (= action "CALCULATE") (bht:progress-plan seg route)))
          (cond ((and plan (eq (car plan) 'LOI)) (bht:err (cadr plan)))
            ((and plan (null (nth 2 plan))) (bht:progress-preview-open (strcat "Không có hồ sơ đủ điều kiện cho " seg) plan) (bht:msg "Không thay đổi dữ liệu. Kiểm tra phía đường, phạm vi và đoạn đang gán."))
            ((or (null plan) (= (bht:progress-preview-open (strcat "Tính bổ sung " seg ": " (itoa (length (nth 2 plan))) " hồ sơ") plan) "OK"))
              (setq own (= 0 (logand 8 (getvar "UNDOCTL")))) (if own (command-s "_.UNDO" "_Begin"))
              (setq result (cond ((= action "CALCULATE") (bht:progress-apply plan))
                ((= action "FINISH") (bht:kh-display-transaction 'bht:progress-finish (list seg)))
                (T (bht:kh-display-transaction 'bht:progress-reopen (list seg)))))
              (if own (command-s "_.UNDO" "_End")) (setq own nil)
              (if (eq (car result) 'LOI) (bht:err (cadr result)) (bht:msg (cadr result)))))))))
  (princ))

(defun c:BHTGOITHAU ()
  (if (bht:palette-load) (command "BHTNAPDOAN") (bht:err "Không nạp được giao diện BHT. Kiểm tra DLL cùng phiên bản.")) (princ))
(defun bht:seg-partition-write (/ r)
  (setq r (bht:station-objects-base))
  (if (eq (car r) 'LOI) r (bht:assign-segments-write)))
(defun c:BHTPHANDOAN (/ *error* r doc own)
  (defun *error* (msg) (if own (vla-EndUndoMark doc)) (bht:on-error msg))
  (if (null (bht:rec-keys "SEG")) (bht:warn "Chưa có bảng đoạn. Chạy BHTGOITHAU trước.")
    (progn
      (setq doc (vla-get-ActiveDocument (vlax-get-acad-object)) own (= 0 (logand 8 (getvar "UNDOCTL"))))
      (if own (vla-StartUndoMark doc))
      (setq r (bht:kh-display-transaction 'bht:seg-partition-write nil))
      (if own (vla-EndUndoMark doc)) (setq own nil)
      (if (eq (car r) 'LOI) (bht:err (cadr r))
        (bht:msg (strcat "Phân đoạn: tự động " (itoa (cdr (assoc 'auto r))) ", nhiều đoạn " (itoa (cdr (assoc 'ambiguous r)))
          ", ngoài phạm vi hoặc khác phía đường " (itoa (cdr (assoc 'outside r))) ", chưa xác định Km " (itoa (cdr (assoc 'undetermined r)))
          ", gán tay giữ nguyên " (itoa (cdr (assoc 'manual r))) ". Hai tim gần bằng nhau hoặc chung mốc biên: chọn đoạn bằng BHTGANDOAN.")))))
  (bht:log-flush) (princ))
(defun bht:seg-unassign-write (oid)
  (if (bht:obj-write oid (bht:seg-clear (bht:obj-read oid) "CHUA_PHAN_DOAN" ""))
    (progn (bht:kh-station-label-refresh (list oid)) (list T)) (list 'LOI "Không bỏ được gán đoạn.")))
(defun c:BHTGANDOAN (/ *error* oid v result own)
  (defun *error* (msg) (if own (command-s "_.UNDO" "_End")) (bht:on-error msg))
  (setq v "")
  (if (setq oid (bht:pick-object "Chọn hồ sơ cần gán đoạn"))
    (progn
      (bht:msg (strcat oid ": " (bht:get (bht:obj-read oid) "ly_trinh_km") " | ứng viên: " (bht:get (bht:obj-read oid) "doan_ung_vien")))
      (if (bht:palette-load)
        (progn (setq result (BHTSEGMENTPICK oid))
          (cond ((= (car result) "SELECT") (setq v (cadr result)))
                ((= (car result) "CLEAR") (setq v "X"))
                ((= (car result) "LOI") (bht:err (cadr result)))))
        (bht:err "Không mở được bảng chọn đoạn. Kiểm tra DLL cùng phiên bản."))
      (if (/= v "")
        (progn
          (setq own (= 0 (logand 8 (getvar "UNDOCTL"))))
          (if own (command-s "_.UNDO" "_Begin"))
          (if (= v "X")
            (progn (setq result (bht:kh-display-transaction 'bht:seg-unassign-write (list oid))) (if (eq (car result) 'LOI) (bht:err (cadr result))))
            (progn (setq result (bht:assign-manual oid v)) (if (car result) (bht:msg (strcat oid " -> " v)) (bht:err (cadr result)))))
          (if own (command-s "_.UNDO" "_End")) (setq own nil)))))
  (bht:log-flush) (princ))
